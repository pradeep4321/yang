/*
 * Generated by confdc --mib2yang-std
 * Source: /Users/janl/git/cia/capp/NetworkElementSynchronizer/../../mibs/mib-source/CISCO-FRAME-RELAY-MIB.mib
 */
/*
 * This YANG module has been generated by smidump 0.5.0:
 *
 *      smidump -f yang CISCO-FRAME-RELAY-MIB
 *
 * Do not edit. Edit the source file instead!
 */

module CISCO-FRAME-RELAY-MIB {

  namespace "urn:ietf:params:xml:ns:yang:smiv2:CISCO-FRAME-RELAY-MIB";
  prefix "cisco-frame";

  import IF-MIB {
    prefix "if-mib";
  }

  import RFC1213-MIB {
    prefix "rfc1213-mib";
  }

  import RFC1315-MIB {
    prefix "rfc1315-mib";
  }

  import SNMPv2-TC {
    prefix "snmpv2-tc";
  }

  import ietf-inet-types {
    prefix "inet";
  }

  import ietf-yang-smiv2 {
    prefix "smiv2";
  }

  import ietf-yang-types {
    prefix "yang";
  }

  organization
   "Cisco Systems, Inc.";

  contact
   "       Cisco Systems
    Customer Service
    
    Postal: 170 W Tasman Drive
    San Jose, CA  95134
    USA
    
    Tel: +1 800 553-NETS
    
    E-mail: cs-framerelay@cisco.com";

  description
   "Cisco Frame Relay MIB";

  revision 2000-10-13 {
    description
     "(1) Added objects of FR Switching, FR Fragmentation 
      and FR/ATM Interworking.
      (2) Objects for per PVC I/O rate is added to 
      cfrExtCircuitTable";
  }

  revision 2000-05-22 {
    description
     "(1) Added  ELMI subgroup for ELMI objects.";
  }

  revision 2000-05-16 {
    description
     "(1) Added Traffic Shaping parameter objects to
      cfrExtCircuitTable.
      (2) Deprecated cfrSvcMinThruputOut and 
      cfrSvcMinThruputIn. Added cfrExtCircuitMinThruputOut 
      and cfrExtCircuitMinThruputIn in cfrExtCircuitTable 
      inorder to make them applicable to both PVC/SVC. 
      (3) Added cfrExtCircuitBandwidth object to 
      cfrExtCircuitTable.";
  }

  revision 2000-04-26 {
    description
     "(1) add an integer value for cfrMapPayloadCompressType;
      (2) reword the Description statements for 
            { cfrMapPayloadCompressType,
            cfrExtCircuitUncompressIns,
            cfrExtCircuitUncompressOuts }
      so that they are not limited to software compression.";
  }

  revision 1999-08-21 {
    description
     "(1) Added cfrExtCircuitUncompressOuts and
      cfrExtCircuitUncompressIns to the circuit subgroup;
      (2) Added cfrMapRtpHdrCompress and cfrMapPayloadCompressType
      to the mapping subgroup;
      (3) cfrMapPayloadCompress becomes deprecated, obsoleted
      by cfrMapPayloadCompressType;
      (4) frCircuitSentOctets and frCircuitReceivedOctets
      per RFC1315 will reflect the number of bytes in Frame Relay
      frames sent to and received from the physical layer. Same
      effect is applied to ifOutOctets and ifInOctets as well
      when ifIndex refers to a Frame Relay subinterface.";
  }

  revision 1996-08-15 {
    description
     "Initial version of this MIB module.";
  }

  typedef DlciNumber {
    type int32 {
      range "0..1023";
    }
    description
     "Numerical format of Data Link Connection Identifier
      (DLCI) in decimal, identical to the 'DLCI' as INTEGER
      of 0..DLCINumber in RFC1315. The maximum value depends
      on Frame Relay implementation, which is currently set
      to be 1023 for 2-octet address format per UNI
      Implementation Agreement FRF.1.";
  }

  typedef CfrMapProtocols {
    type enumeration {
      enum "arp" {
        value "1";
      }
      enum "serialArp" {
        value "6";
      }
      enum "ip" {
        value "7";
      }
      enum "xns" {
        value "10";
      }
      enum "novell" {
        value "11";
      }
      enum "apollo" {
        value "12";
      }
      enum "vines" {
        value "13";
      }
      enum "appletalk" {
        value "16";
      }
      enum "ieeeSpanning" {
        value "18";
      }
      enum "decnet" {
        value "22";
      }
      enum "clns" {
        value "25";
      }
      enum "rsrb" {
        value "37";
      }
      enum "bridge" {
        value "38";
      }
      enum "stun" {
        value "39";
      }
      enum "frArp" {
        value "40";
      }
      enum "uncompressedTcp" {
        value "47";
      }
      enum "compressedTcp" {
        value "48";
      }
      enum "llc2" {
        value "49";
      }
      enum "frSwitch" {
        value "53";
      }
      enum "dlsw" {
        value "63";
      }
      enum "nhrp" {
        value "74";
      }
      enum "compressedRtp" {
        value "83";
      }
      enum "wildcard" {
        value "999";
      }
    }
    description
     "Cisco link types (network protocols) that run
      over Frame Relay. Associated values, except for
      wildcard, match assigned values of internal software
      respectively.";
  }


  container CISCO-FRAME-RELAY-MIB {
    config false;

    container cfrElmiObjs {
      smiv2:oid "1.3.6.1.4.1.9.9.49.1.5";

      leaf cfrElmiIpAddr {
        type inet:ipv4-address;
        description
         "This object represents the Management address of the
          device used for address registration. 
          Network management station can send management
          messages to this IP address. This can be 
          user configured address or the address of one of the
          interfaces on the device. If address registration is
          disabled then this will have a value of 0.0.0.0. 
          This object is accessible only if the ELMI protocol 
          is supported on the device";
        smiv2:max-access "read-only";
        smiv2:oid "1.3.6.1.4.1.9.9.49.1.5.1";
      }
    }

    container cfrMapTable {
      description
       "Table of protocols and addresses mapping
        information of FR virtual circuit.";
      smiv2:oid "1.3.6.1.4.1.9.9.49.1.3.1";

      list cfrMapEntry {
        key "frCircuitIfIndex frCircuitDlci cfrMapIndex";
        description
         "Each entry of the table contains one mapping 
          information of a Frame Relay virtual circuit.";
        smiv2:oid "1.3.6.1.4.1.9.9.49.1.3.1.1";

        leaf frCircuitIfIndex {
          type leafref {
            path "/rfc1315-mib:RFC1315-MIB/rfc1315-mib:frCircuitTable/rfc1315-mib:frCircuitEntry/rfc1315-mib:frCircuitIfIndex";
          }
        }

        leaf frCircuitDlci {
          type leafref {
            path "/rfc1315-mib:RFC1315-MIB/rfc1315-mib:frCircuitTable/rfc1315-mib:frCircuitEntry/rfc1315-mib:frCircuitDlci";
          }
        }

        leaf cfrMapIndex {
          type int32 {
            range "1..999";
          }
          description
           "An arbitrary Index to the mapping information
            associated with a certain circuit. The maximum
            value is arbitrarily picked which is considered
            sufficient for usual configuration.";
          smiv2:max-access "read-only";
          smiv2:oid "1.3.6.1.4.1.9.9.49.1.3.1.1.1";
        }

        leaf cfrMapProtocol {
          type cisco-frame:CfrMapProtocols;
          description
           "Mapping protocol for this circuit.";
          smiv2:max-access "read-only";
          smiv2:oid "1.3.6.1.4.1.9.9.49.1.3.1.1.2";
        }

        leaf cfrMapAddress {
          type binary {
            length "0..64";
          }
          description
           "Mapping protocol address at remote end for
            this DLCI.
            NOTE: For point-to-point DLCI, the string is fixed
            to be point-to-point.";
          smiv2:max-access "read-only";
          smiv2:oid "1.3.6.1.4.1.9.9.49.1.3.1.1.3";
        }

        leaf cfrMapType {
          type enumeration {
            enum "static" {
              value "1";
            }
            enum "dynamic" {
              value "2";
            }
            enum "svc" {
              value "3";
            }
          }
          description
           "Type for the map creation.";
          smiv2:max-access "read-only";
          smiv2:oid "1.3.6.1.4.1.9.9.49.1.3.1.1.4";
        }

        leaf cfrMapEncaps {
          type enumeration {
            enum "ietf" {
              value "1";
            }
            enum "cisco" {
              value "2";
            }
          }
          description
           "Indication of the encapsulation type for this
            mapping protocol.";
          smiv2:max-access "read-only";
          smiv2:oid "1.3.6.1.4.1.9.9.49.1.3.1.1.5";
        }

        leaf cfrMapBroadcast {
          type boolean;
          description
           "Broadcast enabled or disabled.";
          smiv2:max-access "read-only";
          smiv2:oid "1.3.6.1.4.1.9.9.49.1.3.1.1.6";
        }

        leaf cfrMapPayloadCompress {
          type boolean;
          status deprecated;
          description
           "Indicate if payload compression is enabled.";
          smiv2:max-access "read-only";
          smiv2:oid "1.3.6.1.4.1.9.9.49.1.3.1.1.7";
        }

        leaf cfrMapTcpHdrCompress {
          type enumeration {
            enum "inapplicable" {
              value "1";
            }
            enum "passive" {
              value "2";
            }
            enum "active" {
              value "3";
            }
          }
          description
           "TCP header compression type, if applicable.";
          smiv2:max-access "read-only";
          smiv2:oid "1.3.6.1.4.1.9.9.49.1.3.1.1.8";
        }

        leaf cfrMapRtpHdrCompress {
          type enumeration {
            enum "inapplicable" {
              value "1";
            }
            enum "passive" {
              value "2";
            }
            enum "active" {
              value "3";
            }
          }
          description
           "RTP header compression type, if applicable.
            The value 'passive' means that the header of an
            outgoing RTP/IP packet is compressed only if an
            incoming RTP/IP packet had a compressed header.
            The value 'active' means the header of every outgoing
            RTP/IP packet is compressed.";
          smiv2:max-access "read-only";
          smiv2:oid "1.3.6.1.4.1.9.9.49.1.3.1.1.9";
        }

        leaf cfrMapPayloadCompressType {
          type enumeration {
            enum "inapplicable" {
              value "1";
            }
            enum "cisco" {
              value "2";
            }
            enum "frf9Software" {
              value "3";
            }
            enum "frf9Hardware" {
              value "4";
            }
          }
          description
           "FR payload compression type, if applicable.
            FRF.9 is the Frame Relay Forum Implementation Agreement
            on FR payload compression. The compression can be done
            by either software or hardware (when equipped with the
            supporting hardware), depending on configuration.";
          reference
           "Frame Relay Forum document number FRF.9";
          smiv2:max-access "read-only";
          smiv2:oid "1.3.6.1.4.1.9.9.49.1.3.1.1.10";
        }
      }
    }

    container cfrSvcTable {
      description
       "Table of FR SVC specific, descriptive
        and statistics information.";
      smiv2:oid "1.3.6.1.4.1.9.9.49.1.4.1";

      list cfrSvcEntry {
        key "frCircuitIfIndex frCircuitDlci";
        description
         "Each entry of the table contains circuit information
          specific to a Frame Relay Switched Virtual Circuit.";
        smiv2:oid "1.3.6.1.4.1.9.9.49.1.4.1.1";

        leaf frCircuitIfIndex {
          type leafref {
            path "/rfc1315-mib:RFC1315-MIB/rfc1315-mib:frCircuitTable/rfc1315-mib:frCircuitEntry/rfc1315-mib:frCircuitIfIndex";
          }
        }

        leaf frCircuitDlci {
          type leafref {
            path "/rfc1315-mib:RFC1315-MIB/rfc1315-mib:frCircuitTable/rfc1315-mib:frCircuitEntry/rfc1315-mib:frCircuitDlci";
          }
        }

        leaf cfrSvcAddrLocal {
          type binary {
            length "0..64";
          }
          description
           "Local E.164/X.125 address for the circuit.";
          smiv2:max-access "read-only";
          smiv2:oid "1.3.6.1.4.1.9.9.49.1.4.1.1.1";
        }

        leaf cfrSvcAddrRemote {
          type binary {
            length "0..64";
          }
          description
           "Remote E.164/X.125 address for the circuit.";
          smiv2:max-access "read-only";
          smiv2:oid "1.3.6.1.4.1.9.9.49.1.4.1.1.2";
        }

        leaf cfrSvcThroughputIn {
          type int32 {
            range "9600..1544000";
          }
          units "bits per second";
          description
           "Circuit's incoming throughput. For outgoing 
            throughput (commonly referred to as CIR) see
            frCircuitThroughput per RFC1315.";
          smiv2:max-access "read-only";
          smiv2:oid "1.3.6.1.4.1.9.9.49.1.4.1.1.3";
        }

        leaf cfrSvcMinThruputOut {
          type int32 {
            range "9600..1544000";
          }
          units "bits per second";
          status deprecated;
          description
           "Circuit's outgoing minimal Throughput.";
          smiv2:max-access "read-only";
          smiv2:oid "1.3.6.1.4.1.9.9.49.1.4.1.1.4";
        }

        leaf cfrSvcMinThruputIn {
          type int32 {
            range "9600..1544000";
          }
          units "bits per second";
          status deprecated;
          description
           "Circuit's incoming minimal Throughput.";
          smiv2:max-access "read-only";
          smiv2:oid "1.3.6.1.4.1.9.9.49.1.4.1.1.5";
        }

        leaf cfrSvcCommitBurstIn {
          type int32 {
            range "9600..1544000";
          }
          description
           "Circuit's incoming Committed Burst Rate.
            See ANSI and/or ITU specifications for
            definition and calculations. For outgoing
            CBR, see frCircuitCommittedBurst per RFC 1315.";
          smiv2:max-access "read-only";
          smiv2:oid "1.3.6.1.4.1.9.9.49.1.4.1.1.6";
        }

        leaf cfrSvcExcessBurstIn {
          type int32 {
            range "9600..2440000";
          }
          description
           "Circuit's incoming Excess Burst Rate.
            See ANSI and/or ITU specifications for
            definition and calculations. For outgoing
            EBR, see frCircuitExcessBurst per RFC 1315.";
          smiv2:max-access "read-only";
          smiv2:oid "1.3.6.1.4.1.9.9.49.1.4.1.1.7";
        }

        leaf cfrSvcIdleTime {
          type int32;
          units "seconds";
          description
           "Circuit's idle time period. If expires, the
            circuit is cleared.";
          smiv2:max-access "read-only";
          smiv2:oid "1.3.6.1.4.1.9.9.49.1.4.1.1.8";
        }
      }
    }

    container cfrElmiTable {
      description
       "Table of CISCO Frame Relay ELMI information that is
        specific to CISCO implementation";
      smiv2:oid "1.3.6.1.4.1.9.9.49.1.5.2";

      list cfrElmiEntry {
        key "ifIndex";
        description
         "Each entry of the table contains information about a
          physical interface. The table can be accessible only
          if the device supports ELMI protocol and if LMI is
          enabled on the interface.";
        smiv2:oid "1.3.6.1.4.1.9.9.49.1.5.2.1";

        leaf ifIndex {
          type leafref {
            path "/if-mib:IF-MIB/if-mib:ifTable/if-mib:ifEntry/if-mib:ifIndex";
          }
        }

        leaf cfrElmiLinkStatus {
          type enumeration {
            enum "enabled" {
              value "1";
            }
            enum "disabled" {
              value "2";
            }
          }
          description
           "This variable states whether Enhanced Link Management
            Interface(ELMI) protocol is enabled or not on a 
            frame relay interface.";
          smiv2:max-access "read-only";
          smiv2:oid "1.3.6.1.4.1.9.9.49.1.5.2.1.1";
        }

        leaf cfrElmiArStatus {
          type enumeration {
            enum "enabled" {
              value "1";
            }
            enum "disabled" {
              value "2";
            }
          }
          description
           "This variable states whether the Enhanced Link
            Management Interface(ELMI) address registration(AR)
            mechanism is enabled or not on a frame relay 
            interface. A value of 1 indicates ELMI AR is 
            supported on the interface. A value of 2 indicates
            ELMI AR is supported but the user disabled the
            exchange of IP address and ifIndex with the
            neighboring device. This object doesn't have any
            significance if cfrElmiLinkStatus is disabled
            on the interface.";
          smiv2:max-access "read-only";
          smiv2:oid "1.3.6.1.4.1.9.9.49.1.5.2.1.2";
        }

        leaf cfrElmiRemoteStatus {
          type enumeration {
            enum "enabled" {
              value "1";
            }
            enum "disabled" {
              value "2";
            }
          }
          description
           "This variable states the Enhanced Link 
            Management(ELMI) status on the other end of the
            interface. If cfrElmiLinkStatus is enabled on the
            other end a value of 1 will be returned,
            else 2 will be returned. This object doesn't have any
            significance if cfrElmiLinkStatus is disabled on the
            interface";
          smiv2:max-access "read-only";
          smiv2:oid "1.3.6.1.4.1.9.9.49.1.5.2.1.3";
        }
      }
    }

    container cfrElmiNeighborTable {
      description
       "Table of CISCO Frame Relay Neighbor ELMI information
        that is specific to CISCO implementation.";
      smiv2:oid "1.3.6.1.4.1.9.9.49.1.5.3";

      list cfrElmiNeighborEntry {
        key "ifIndex";
        description
         "Each entry of the table contains information of the
          neighboring device connected to a physical interface.
          The entry will be present only if ELMI is enabled on
          the neighboring device interface. If the value of the
          cfrElmiRemoteStatus in the cfrElmiEntry is 1 then a 
          valid entry exists for the interface. If ELMI is not 
          supported on the remote end then, the neighbor 
          information for the interface will not be present";
        smiv2:oid "1.3.6.1.4.1.9.9.49.1.5.3.1";

        leaf ifIndex {
          type leafref {
            path "/if-mib:IF-MIB/if-mib:ifTable/if-mib:ifEntry/if-mib:ifIndex";
          }
        }

        leaf cfrElmiNeighborArStatus {
          type enumeration {
            enum "notsupported" {
              value "1";
            }
            enum "enabled" {
              value "2";
            }
            enum "disabled" {
              value "3";
            }
          }
          description
           "This variable indicates the status of ELMI Address 
            registration(AR) on the neighboring device. A value 
            of 1 indicates ELMI AR is not supported on the 
            neighboring device. A value of 2 indicates ELMI AR is
            enabled on the interface. A value of 3 indicates AR is
            supported, but user disabled the exchange of IP 
            address and ifIndex with the neighbor.";
          smiv2:max-access "read-only";
          smiv2:oid "1.3.6.1.4.1.9.9.49.1.5.3.1.1";
        }

        leaf cfrElmiNeighborIpAddress {
          type inet:ipv4-address;
          description
           "The Management IP address of the neighboring device 
            to which the other end of this interface is 
            connected. Network management system can use this
            address to send management messages to the device.
            If address registration is not supported on the
            remote end then the value will be 0.0.0.0.
            NMS uses this object in the topology discovery of the
            network.";
          smiv2:max-access "read-only";
          smiv2:oid "1.3.6.1.4.1.9.9.49.1.5.3.1.2";
        }

        leaf cfrElmiNeighborIfIndex {
          type if-mib:InterfaceIndex;
          description
           "The Interface index of the neighboring device to 
            which this interface is connected. If the value of
            cfrElmiNeighborArStatus is 2 then this will have a
            valid value. If the value of cfrElmiNeighborArStatus
            is 3 or 1 then value of this object will be 0. NMS
            uses this object in the topology discovery of the
            network.";
          smiv2:max-access "read-only";
          smiv2:oid "1.3.6.1.4.1.9.9.49.1.5.3.1.3";
        }

        leaf cfrElmiNeighborVendorName {
          type snmpv2-tc:DisplayString;
          description
           "Vendor name of the neighboring device to which the
            other end of this interface is connected.";
          smiv2:max-access "read-only";
          smiv2:oid "1.3.6.1.4.1.9.9.49.1.5.3.1.4";
        }

        leaf cfrElmiNeighborPlatformName {
          type snmpv2-tc:DisplayString;
          description
           "Platform name of the neighboring device to which the
            other end of this interface is connected.";
          smiv2:max-access "read-only";
          smiv2:oid "1.3.6.1.4.1.9.9.49.1.5.3.1.5";
        }

        leaf cfrElmiNeighborDeviceName {
          type snmpv2-tc:DisplayString;
          description
           "Device name of the neighboring device to which the
            other end of this interface is connected.";
          smiv2:max-access "read-only";
          smiv2:oid "1.3.6.1.4.1.9.9.49.1.5.3.1.6";
        }
      }
    }

    container cfrFragTable {
      description
       "Table of Frame Relay Fragmentation information. 
        These are specific to Cisco's implementation.";
      smiv2:oid "1.3.6.1.4.1.9.9.49.1.6.1";

      list cfrFragEntry {
        key "frCircuitIfIndex frCircuitDlci";
        description
         "Each entry of the table contains details of 
          fragmentation configured on  this circuit. ";
        smiv2:oid "1.3.6.1.4.1.9.9.49.1.6.1.1";

        leaf frCircuitIfIndex {
          type leafref {
            path "/rfc1315-mib:RFC1315-MIB/rfc1315-mib:frCircuitTable/rfc1315-mib:frCircuitEntry/rfc1315-mib:frCircuitIfIndex";
          }
        }

        leaf frCircuitDlci {
          type leafref {
            path "/rfc1315-mib:RFC1315-MIB/rfc1315-mib:frCircuitTable/rfc1315-mib:frCircuitEntry/rfc1315-mib:frCircuitDlci";
          }
        }

        leaf cfrFragSize {
          type int32 {
            range "16..1600";
          }
          units "octets";
          description
           "cfrFragSize defines the payload size of a fragment 
            and it excludes the FR headers and any FR fragmentation
            header.";
          smiv2:max-access "read-only";
          smiv2:oid "1.3.6.1.4.1.9.9.49.1.6.1.1.1";
        }

        leaf cfrFragType {
          type snmpv2-tc:DisplayString;
          description
           "Fragmentation type configured by the user. The types
            supported are end-to-end, VoFR-cisco and VoFR.";
          smiv2:max-access "read-only";
          smiv2:oid "1.3.6.1.4.1.9.9.49.1.6.1.1.2";
        }

        leaf cfrFragInPkts {
          type yang:counter32;
          units "packets";
          description
           "Total number of frames received that have a 
            fragmentation header.";
          smiv2:max-access "read-only";
          smiv2:oid "1.3.6.1.4.1.9.9.49.1.6.1.1.3";
        }

        leaf cfrFragOutPkts {
          type yang:counter32;
          units "packets";
          description
           "Total number of fragments that are transmitted with a
            fragmenation header.";
          smiv2:max-access "read-only";
          smiv2:oid "1.3.6.1.4.1.9.9.49.1.6.1.1.4";
        }

        leaf cfrFragInOctets {
          type yang:counter32;
          units "octets";
          description
           "Total number of bytes received in frames that have a 
            fragmentation header. The number of bytes include the
            FR header.";
          smiv2:max-access "read-only";
          smiv2:oid "1.3.6.1.4.1.9.9.49.1.6.1.1.5";
        }

        leaf cfrFragOutOctets {
          type yang:counter32;
          units "octets";
          description
           "Total number of bytes that are transmitted in frames
            with a fragmenation header. The number of bytes also
            includes the FR header.";
          smiv2:max-access "read-only";
          smiv2:oid "1.3.6.1.4.1.9.9.49.1.6.1.1.6";
        }

        leaf cfrFragNotInPkts {
          type yang:counter32;
          units "packets";
          description
           "Total number of frames received that do not require 
            reassembly and therefore will not contain the 
            fragmentation header. This counter is valid only when
            end-to-end fragmentation type is set.";
          smiv2:max-access "read-only";
          smiv2:oid "1.3.6.1.4.1.9.9.49.1.6.1.1.7";
        }

        leaf cfrFragNotOutPkts {
          type yang:counter32;
          units "packets";
          description
           "Total number of frames transmitted without fragmenting
            and therefore will not contain the fragmentation header.
            This counter is valid only when end-to-end fragmentation
            type is set.";
          smiv2:max-access "read-only";
          smiv2:oid "1.3.6.1.4.1.9.9.49.1.6.1.1.8";
        }

        leaf cfrFragNotInOctets {
          type yang:counter32;
          units "octets";
          description
           "Total number of bytes received in frames that do not 
            require reassembly and therefore will not contain the 
            fragmentation header. This counter is valid only when
            end-to-end fragmentation type is set.";
          smiv2:max-access "read-only";
          smiv2:oid "1.3.6.1.4.1.9.9.49.1.6.1.1.9";
        }

        leaf cfrFragNotOutOctets {
          type yang:counter32;
          units "octets";
          description
           "Total number of bytes transmitted in frames that are
            not fragmented and therefore will not contain the 
            fragmentation header. This counter is valid only when 
            end-to-end fragmentation type is set.";
          smiv2:max-access "read-only";
          smiv2:oid "1.3.6.1.4.1.9.9.49.1.6.1.1.10";
        }

        leaf cfrFragAssembledInPkts {
          type yang:counter32;
          units "packets";
          description
           "Total number of fully reassembled frames. It also 
            counts the number of packets received without FR 
            fragmentation header (i.e. in un-fragmentated pkts).";
          smiv2:max-access "read-only";
          smiv2:oid "1.3.6.1.4.1.9.9.49.1.6.1.1.11";
        }

        leaf cfrFragAssembledInOctets {
          type yang:counter32;
          units "octets";
          description
           "Total number of bytes received in fully reassembled 
            frames. It also counts the number of packets received
            without FR fragmentation header (i.e.in un-fragmentated
            pkts).";
          smiv2:max-access "read-only";
          smiv2:oid "1.3.6.1.4.1.9.9.49.1.6.1.1.12";
        }

        leaf cfrFragPreOutPkts {
          type yang:counter32;
          units "packets";
          description
           "Total number of frames fragmented and trasmitted. It 
            also counts the number of packets trasmitted without FR
            fragmentation header (i.e. in un-fragmentated pkts).";
          smiv2:max-access "read-only";
          smiv2:oid "1.3.6.1.4.1.9.9.49.1.6.1.1.13";
        }

        leaf cfrFragPreOutOctets {
          type yang:counter32;
          units "octets";
          description
           "Total number of bytes transmitted in fragmented frames.
            It also counts the number of bytes trasmitted in frames
            without FR fragmentation header (i.e. in un-fragmentated
            pkts).";
          smiv2:max-access "read-only";
          smiv2:oid "1.3.6.1.4.1.9.9.49.1.6.1.1.14";
        }

        leaf cfrFragDroppedReAssembledInPkts {
          type yang:counter32;
          units "packets";
          description
           "Number of received fragments dropped for reasons such
            as : running out of memory, receiving segments out of 
            sequence, receiving an unexpected frame with a B bit 
            set, timing out on a reassembling frame.";
          smiv2:max-access "read-only";
          smiv2:oid "1.3.6.1.4.1.9.9.49.1.6.1.1.15";
        }

        leaf cfrFragDroppedFragmentedOutPkts {
          type yang:counter32;
          units "packets";
          description
           "Number of fragments dropped because of running 
            out of memory.";
          smiv2:max-access "read-only";
          smiv2:oid "1.3.6.1.4.1.9.9.49.1.6.1.1.16";
        }

        leaf cfrFragTimeoutsIn {
          type int32 {
            range "0..1000";
          }
          description
           "Number of reassemble timer timeouts for this circuit.
            A frame requiring more than two minutes to fully 
            reassemble is dropped and timeout will be incremented
            by one.";
          smiv2:max-access "read-only";
          smiv2:oid "1.3.6.1.4.1.9.9.49.1.6.1.1.17";
        }

        leaf cfrFragOutOfSeqFragPkts {
          type yang:counter32;
          units "packets";
          description
           "Indicates the total number of packets received with an
            unexpected sequence number. All fragments being 
            reassembled are dropped. Start a new packet with the
            received segment only if the B bit is set on the 
            segment. Otherwise the new segment is also dropped.";
          smiv2:max-access "read-only";
          smiv2:oid "1.3.6.1.4.1.9.9.49.1.6.1.1.18";
        }

        leaf cfrFragUnexpectedBBitSetPkts {
          type yang:counter32;
          units "packets";
          description
           "Number of fragments received in this circuit with 
            a B bit set. All fragments being reassembled are dropped
            and a new packet is started with this segment.";
          smiv2:max-access "read-only";
          smiv2:oid "1.3.6.1.4.1.9.9.49.1.6.1.1.19";
        }

        leaf cfrFragSeqMissedPkts {
          type yang:counter32;
          units "packets";
          description
           "Number of fragments received in this circuit with 
            skipped sequence number.";
          smiv2:max-access "read-only";
          smiv2:oid "1.3.6.1.4.1.9.9.49.1.6.1.1.20";
        }

        leaf cfrFragInterleavedOutPkts {
          type yang:counter32;
          units "packets";
          description
           "Number of packets that have been interleaved between 
            segments.";
          smiv2:max-access "read-only";
          smiv2:oid "1.3.6.1.4.1.9.9.49.1.6.1.1.21";
        }
      }
    }

    container cfrConnectionTable {
      description
       "Table of Frame Relay/Frame Relay and Frame Relay/ATM
        Network/Service Interworking connection information. 
        These are specific to Cisco's implementation.";
      smiv2:oid "1.3.6.1.4.1.9.9.49.1.7.1";

      list cfrConnectionEntry {
        key "frCircuitIfIndex frCircuitDlci";
        description
         "Each entry of the table contains information of a
          connection that is established for Frame Relay/Frame 
          Relay and Frame Relay/ATM Network/Service Interworking.";
        smiv2:oid "1.3.6.1.4.1.9.9.49.1.7.1.1";

        leaf frCircuitIfIndex {
          type leafref {
            path "/rfc1315-mib:RFC1315-MIB/rfc1315-mib:frCircuitTable/rfc1315-mib:frCircuitEntry/rfc1315-mib:frCircuitIfIndex";
          }
        }

        leaf frCircuitDlci {
          type leafref {
            path "/rfc1315-mib:RFC1315-MIB/rfc1315-mib:frCircuitTable/rfc1315-mib:frCircuitEntry/rfc1315-mib:frCircuitDlci";
          }
        }

        leaf cfrConnName {
          type snmpv2-tc:DisplayString;
          description
           "The textual name of a for FR/FR or FR/ATM  
            Network/Service Interworking connection.";
          smiv2:max-access "read-only";
          smiv2:oid "1.3.6.1.4.1.9.9.49.1.7.1.1.1";
        }

        leaf cfrConnID {
          type int32 {
            range "1..2000";
          }
          description
           "The numerical identifier of a FR/FR or FR/ATM  
            Network/Service Interworking connection.";
          smiv2:max-access "read-only";
          smiv2:oid "1.3.6.1.4.1.9.9.49.1.7.1.1.2";
        }

        leaf cfrConnState {
          type snmpv2-tc:DisplayString;
          description
           "Status of a FR/FR or FR/ATM  Network/Service 
            Interworking connection.";
          smiv2:max-access "read-only";
          smiv2:oid "1.3.6.1.4.1.9.9.49.1.7.1.1.3";
        }

        leaf cfrConnSegment1Name {
          type snmpv2-tc:DisplayString;
          description
           "The textual name used to identify the first segment of 
            a FR/FR or FR/ATM  Network/Service Interworking 
            connection.";
          smiv2:max-access "read-only";
          smiv2:oid "1.3.6.1.4.1.9.9.49.1.7.1.1.4";
        }

        leaf cfrConnSegment1VCGroup {
          type snmpv2-tc:DisplayString;
          description
           "The textual name used to identify the VC-Group in the
            first segment of a Frame Relay/ATM  Network Interworking
            (FRF.5)connection. 
            This field is not applicabe in case of,
                     FRF.8 (Frame Relay/ATM  Service Interworking)
                     and
                     FR-FR connectione. ";
          smiv2:max-access "read-only";
          smiv2:oid "1.3.6.1.4.1.9.9.49.1.7.1.1.5";
        }

        leaf cfrConnSegment1Dlci {
          type cisco-frame:DlciNumber;
          description
           "The DLCI used as the first segment of a FR-FR or FR-ATM
            Network/Service Interworking connection.";
          smiv2:max-access "read-only";
          smiv2:oid "1.3.6.1.4.1.9.9.49.1.7.1.1.6";
        }

        leaf cfrConnSegment2Name {
          type snmpv2-tc:DisplayString;
          description
           "The interface on which second segment of a FR-FR or 
            FR-ATM  Network/Service Interworking connection is 
            configured.";
          smiv2:max-access "read-only";
          smiv2:oid "1.3.6.1.4.1.9.9.49.1.7.1.1.7";
        }

        leaf cfrConnSegment2Vpi {
          type int32 {
            range "0..4095";
          }
          description
           "The value of  VPI, in the ATM connection, used as the
            second segment of a FR-ATM  Network/Service Interworking
            connection. In case of FR-FR connection, the same will 
            be used to display the DLCI used as the second segment.";
          smiv2:max-access "read-only";
          smiv2:oid "1.3.6.1.4.1.9.9.49.1.7.1.1.8";
        }

        leaf cfrConnSegment2Vci {
          type int32 {
            range "0..4095";
          }
          description
           "The value of  VCI, in the ATM connection, used as the
            second segment of a FR-ATM  Network/Service Interworking
            connection. In case of FR-FR connection, this is not 
            supported.";
          smiv2:max-access "read-only";
          smiv2:oid "1.3.6.1.4.1.9.9.49.1.7.1.1.9";
        }

        leaf cfrConnServiceTranslation {
          type enumeration {
            enum "serviceTranslationEnabled" {
              value "1";
            }
            enum "serviceTranslationNotEnabled" {
              value "2";
            }
          }
          description
           "Shows whether Service Translation Mode is supported or
            not. Translation Mode is the interworking of 
            internetworking (routed and/or bridged) protocols used 
            in FR-ATM  Service PVC Interworking(FRF.8).
            This is not supported in case of FRF.5 (FR-ATM network
            Interworking) and FR-FR connections.";
          smiv2:max-access "read-only";
          smiv2:oid "1.3.6.1.4.1.9.9.49.1.7.1.1.10";
        }

        leaf cfrConnFrSscsDlci {
          type cisco-frame:DlciNumber;
          description
           "The DLCI value used at the FR-SSCS layer. This is one of
            connection multiplexing methods used in Frame Relay/ATM  
            Network Interworking.
            Not supported in case of FRF.8 (FR-ATM Service PVC 
            Interworking) and FR-FR connections";
          smiv2:max-access "read-only";
          smiv2:oid "1.3.6.1.4.1.9.9.49.1.7.1.1.11";
        }

        leaf cfrConnEfciBit {
          type enumeration {
            enum "mapFecn" {
              value "1";
            }
            enum "notMapFecn" {
              value "2";
            }
          }
          description
           "Shows whether the FECN field in the FR frame is mapped 
            to the ATM EFCI field of every cell generated out of the 
            FR frame. This is used to indicate congestion in FR to
            ATM direction in case of Frame Relay/ATM  Service PVC 
            Interworking.
            Not supported in FRF.5 (Frame Relay/ATM Network 
            Interworking and FR-FR connections.";
          smiv2:max-access "read-only";
          smiv2:oid "1.3.6.1.4.1.9.9.49.1.7.1.1.12";
        }

        leaf cfrConnDeBit {
          type enumeration {
            enum "noMapClp" {
              value "1";
            }
            enum "mapClp" {
              value "2";
            }
            enum "setDe0" {
              value "3";
            }
            enum "setDe1" {
              value "4";
            }
          }
          description
           "The method of operation for loss priority mapping in the
            B-ISDN to FR direction..
            Not supported in case of FR-FR connection.";
          smiv2:max-access "read-only";
          smiv2:oid "1.3.6.1.4.1.9.9.49.1.7.1.1.13";
        }

        leaf cfrConnClpBit {
          type enumeration {
            enum "setClpTo0AndCopyDeToFrsscsDe" {
              value "1";
            }
            enum "setClpTo1AndCopyDeToFrsscsDe" {
              value "2";
            }
            enum "copyDeToFrsscsDeAndClp" {
              value "3";
            }
            enum "copyDeToClp" {
              value "4";
            }
            enum "setClp1" {
              value "5";
            }
            enum "setClp0" {
              value "6";
            }
          }
          description
           "The method of operation used to map loss priority
            mapping in the FR to ATM direction.
            Not supported in case of FR-FR connection.";
          smiv2:max-access "read-only";
          smiv2:oid "1.3.6.1.4.1.9.9.49.1.7.1.1.14";
        }
      }
    }
  }

  smiv2:alias "cfrLmiTable" {
    description
     "Table of Frame Relay LMI information that are
      either supplemental to the frDlcmiTable of RFC 1315
      or specific to Cisco's implementation.";
    reference
     "American National Standard T1.617-1991, Annex D";
    smiv2:oid "1.3.6.1.4.1.9.9.49.1.1.1";
  }

  smiv2:alias "cfrLmiEntry" {
    description
     "Each entry of the table contains information
      of Frame Relay LMI over one physical interface.
      They are mostly FR generic and some Cisco specific.";
    smiv2:oid "1.3.6.1.4.1.9.9.49.1.1.1.1";
  }

  augment "/rfc1315-mib:RFC1315-MIB/rfc1315-mib:frDlcmiTable/rfc1315-mib:frDlcmiEntry" {
    description
     "Each entry of the table contains information
      of Frame Relay LMI over one physical interface.
      They are mostly FR generic and some Cisco specific.";
    smiv2:oid "1.3.6.1.4.1.9.9.49.1.1.1.1";

    leaf cfrLmiLinkstatus {
      type enumeration {
        enum "up" {
          value "1";
        }
        enum "down" {
          value "2";
        }
      }
      description
       "Data link status via LMI.";
      smiv2:max-access "read-only";
      smiv2:oid "1.3.6.1.4.1.9.9.49.1.1.1.1.1";
    }

    leaf cfrLmiLinkType {
      type enumeration {
        enum "dte" {
          value "1";
        }
        enum "dce" {
          value "2";
        }
        enum "nni" {
          value "3";
        }
      }
      description
       "Frame Relay link type.";
      smiv2:max-access "read-only";
      smiv2:oid "1.3.6.1.4.1.9.9.49.1.1.1.1.2";
    }

    leaf cfrLmiEnquiryIns {
      type yang:counter32;
      units "messages";
      description
       "Number of Status Enquiry messages received.";
      smiv2:max-access "read-only";
      smiv2:oid "1.3.6.1.4.1.9.9.49.1.1.1.1.3";
    }

    leaf cfrLmiEnquiryOuts {
      type yang:counter32;
      units "messages";
      description
       "Number of Status Enquiry messages sent.";
      smiv2:max-access "read-only";
      smiv2:oid "1.3.6.1.4.1.9.9.49.1.1.1.1.4";
    }

    leaf cfrLmiStatusIns {
      type yang:counter32;
      units "messages";
      description
       "Number of Status messages received.";
      smiv2:max-access "read-only";
      smiv2:oid "1.3.6.1.4.1.9.9.49.1.1.1.1.5";
    }

    leaf cfrLmiStatusOuts {
      type yang:counter32;
      units "messages";
      description
       "Number of Status messages sent.";
      smiv2:max-access "read-only";
      smiv2:oid "1.3.6.1.4.1.9.9.49.1.1.1.1.6";
    }

    leaf cfrLmiUpdateStatusIns {
      type yang:counter32;
      units "messages";
      description
       "Number of Update Status messages received.";
      smiv2:max-access "read-only";
      smiv2:oid "1.3.6.1.4.1.9.9.49.1.1.1.1.7";
    }

    leaf cfrLmiUpdateStatusOuts {
      type yang:counter32;
      units "messages";
      description
       "Number of Update Status messages sent";
      smiv2:max-access "read-only";
      smiv2:oid "1.3.6.1.4.1.9.9.49.1.1.1.1.8";
    }

    leaf cfrLmiStatusTimeouts {
      type yang:counter32;
      units "times";
      description
       "Number of times when timeout occurred on waiting
        for Status message";
      smiv2:max-access "read-only";
      smiv2:oid "1.3.6.1.4.1.9.9.49.1.1.1.1.9";
    }

    leaf cfrLmiStatusEnqTimeouts {
      type yang:counter32;
      units "times";
      description
       "Number of times when timeout occurred on waiting
        for Status Enquiry message";
      smiv2:max-access "read-only";
      smiv2:oid "1.3.6.1.4.1.9.9.49.1.1.1.1.10";
    }

    leaf cfrLmiN392Dce {
      type int32 {
        range "0..10";
      }
      description
       "LMI error threshold for DCE interface.
        For DTE, value becomes 0.";
      smiv2:max-access "read-only";
      smiv2:oid "1.3.6.1.4.1.9.9.49.1.1.1.1.11";
    }

    leaf cfrLmiN393Dce {
      type int32 {
        range "0..10";
      }
      description
       "LMI monitored event count for DCE interface.
        For DTE, value becomes zero (0).";
      smiv2:max-access "read-only";
      smiv2:oid "1.3.6.1.4.1.9.9.49.1.1.1.1.12";
    }

    leaf cfrLmiT392Dce {
      type int32 {
        range "0..30";
      }
      units "seconds";
      description
       "DCE polling verification timer for DCE interface
        For DTE, the value becomes zero (0).";
      smiv2:max-access "read-only";
      smiv2:oid "1.3.6.1.4.1.9.9.49.1.1.1.1.13";
    }
  }

  smiv2:alias "cfrCircuitTable" {
    description
     "Table of descriptive and statistics information
      that are generic to Frame Relay virtual circuits.";
    smiv2:oid "1.3.6.1.4.1.9.9.49.1.2.1";
  }

  smiv2:alias "cfrCircuitEntry" {
    description
     "Each entry of the table contains information of a
      circuit that are not included in frCircuitTable of
      RFC1315 but are generic to Frame Relay.";
    smiv2:oid "1.3.6.1.4.1.9.9.49.1.2.1.1";
  }

  augment "/rfc1315-mib:RFC1315-MIB/rfc1315-mib:frCircuitTable/rfc1315-mib:frCircuitEntry" {
    description
     "Each entry of the table contains information of a
      circuit that are not included in frCircuitTable of
      RFC1315 but are generic to Frame Relay.";
    smiv2:oid "1.3.6.1.4.1.9.9.49.1.2.1.1";

    leaf cfrCircuitDEins {
      type yang:counter32;
      units "packets";
      description
       "Number of packets received with the Discarded
        Eligibility indictor (the DE bit) set.";
      smiv2:max-access "read-only";
      smiv2:oid "1.3.6.1.4.1.9.9.49.1.2.1.1.1";
    }

    leaf cfrCircuitDEouts {
      type yang:counter32;
      units "packets";
      description
       "Number of packets transmitted with DE bit set.";
      smiv2:max-access "read-only";
      smiv2:oid "1.3.6.1.4.1.9.9.49.1.2.1.1.2";
    }

    leaf cfrCircuitDropPktsOuts {
      type yang:counter32;
      units "packets";
      description
       "Number of discarded packets that were to be sent.";
      smiv2:max-access "read-only";
      smiv2:oid "1.3.6.1.4.1.9.9.49.1.2.1.1.3";
    }

    leaf cfrCircuitType {
      type enumeration {
        enum "pvc" {
          value "1";
        }
        enum "svc" {
          value "2";
        }
      }
      description
       "Basic circuit type";
      smiv2:max-access "read-only";
      smiv2:oid "1.3.6.1.4.1.9.9.49.1.2.1.1.4";
    }
  }

  smiv2:alias "cfrExtCircuitTable" {
    description
     "Table of Cisco implementation specific FR
      circuit information. This is a Cisco extension
      for the frCircuitTable of RFC 1315.";
    smiv2:oid "1.3.6.1.4.1.9.9.49.1.2.2";
  }

  smiv2:alias "cfrExtCircuitEntry" {
    description
     "Each entry of the table contains information
      of a Frame Relay virtual circuit that are specific
      to Cisco implementation.";
    smiv2:oid "1.3.6.1.4.1.9.9.49.1.2.2.1";
  }

  augment "/rfc1315-mib:RFC1315-MIB/rfc1315-mib:frCircuitTable/rfc1315-mib:frCircuitEntry" {
    description
     "Each entry of the table contains information
      of a Frame Relay virtual circuit that are specific
      to Cisco implementation.";
    smiv2:oid "1.3.6.1.4.1.9.9.49.1.2.2.1";

    leaf cfrExtCircuitIfName {
      type snmpv2-tc:DisplayString;
      description
       "The textual name of the main interface or the 
        subinterface that this DLCI is associated with.
        This is the same name string of an interface used
        in the configuration and all console displays,
        such as 'serial 0', 'serial 3/0.3', etc.";
      smiv2:max-access "read-only";
      smiv2:oid "1.3.6.1.4.1.9.9.49.1.2.2.1.1";
    }

    leaf cfrExtCircuitIfType {
      type enumeration {
        enum "mainInterface" {
          value "1";
        }
        enum "pointToPoint" {
          value "2";
        }
        enum "multipoint" {
          value "3";
        }
      }
      description
       "Type of the subinterface this DLCI is associated
        with, if configured.";
      smiv2:max-access "read-only";
      smiv2:oid "1.3.6.1.4.1.9.9.49.1.2.2.1.2";
    }

    leaf cfrExtCircuitSubifIndex {
      type if-mib:InterfaceIndex;
      description
       "For value greater than zero (0), it indicates
        the network management interface index
        for the subinterface associated with
        this DLCI. Value 0 means the DLCI is not
        associated with any subinterface.";
      smiv2:max-access "read-only";
      smiv2:oid "1.3.6.1.4.1.9.9.49.1.2.2.1.3";
    }

    leaf cfrExtCircuitMapStatus {
      type int32 {
        range "0..2047";
      }
      description
       "The mapping protocols (internally considered as
        the 'link type') applied on this circuit.
        The value ranges from 0 to 2047.
        For point-to-point DLCI, the value stays zero.
        Otherwise, the value is a sum. It initially takes
        the value zero, then, for each type of Protocol,
        2 raised to a power is added to the sum.
        The following table presents respective power and
        equivalent value for each applicable type:
        
                Protocol        Power    Value
                --------        -----    -----
                IP              0        1
                IPX             1        2
                Appletalk       2        4
                XNS             3        8
                VINES           4        16
                DECnet          5        32
                CLNS            6        64
                Bridging        7        128
                RSRB            8        256
                STUN            9        512
                LLC2            10       1024
        
        For example, value 3 means the circuit's mapping
        protocols include IP and IPX. (3 = 2**1 + 2**0,
        where 0 corresponds to IP and 1 to IPX.) Value 0
        means there is currently no mapping protocol for
        the circuit.
        See cfrMapTable for more mapping information.";
      smiv2:max-access "read-only";
      smiv2:oid "1.3.6.1.4.1.9.9.49.1.2.2.1.4";
    }

    leaf cfrExtCircuitCreateType {
      type enumeration {
        enum "dynamic" {
          value "1";
        }
        enum "static" {
          value "2";
        }
      }
      description
       "Identify the last source of the circuit's creation.";
      smiv2:max-access "read-only";
      smiv2:oid "1.3.6.1.4.1.9.9.49.1.2.2.1.5";
    }

    leaf cfrExtCircuitMulticast {
      type boolean;
      description
       "Indicate if this DLCI is a multicast DLCI.";
      smiv2:max-access "read-only";
      smiv2:oid "1.3.6.1.4.1.9.9.49.1.2.2.1.6";
    }

    leaf cfrExtCircuitRoutedDlci {
      type cisco-frame:DlciNumber;
      description
       "The routed DLCI to pair up with this DLCI
        for switching function. NOTE: Value zero (0)
        indicates that there is no such routed DLCI
        corresponding to this DLCI.";
      smiv2:max-access "read-only";
      smiv2:oid "1.3.6.1.4.1.9.9.49.1.2.2.1.7";
    }

    leaf cfrExtCircuitRoutedIf {
      type if-mib:InterfaceIndex;
      description
       "The interface for the routed DLCI that pairs up
        with this DLCI for switching. Value greater than 0
        is the InterfaceIndex for that interface. Value
        zero (0) indicates that there is no such routed DLCI
        corresponding to this DLCI.";
      smiv2:max-access "read-only";
      smiv2:oid "1.3.6.1.4.1.9.9.49.1.2.2.1.8";
    }

    leaf cfrExtCircuitUncompressIns {
      type yang:counter32;
      units "octets";
      description
       "Number of inbound octets of the data packets,
        accounted at Frame Relay level after FRF.9
        payload decompression is applied. In the case of
        non-FRF.9, this value could be identical to
        frCircuitReceivedOctets, unless otherwise noted.";
      smiv2:max-access "read-only";
      smiv2:oid "1.3.6.1.4.1.9.9.49.1.2.2.1.9";
    }

    leaf cfrExtCircuitUncompressOuts {
      type yang:counter32;
      units "octets";
      description
       "Number of outbound octets of the data packets,
        accounted at Frame Relay level before FRF.9
        payload compression is applied. In the case of
        non-FRF.9, this value could be identical to
        frCircuitSentOctets, unless otherwise noted.";
      smiv2:max-access "read-only";
      smiv2:oid "1.3.6.1.4.1.9.9.49.1.2.2.1.10";
    }

    leaf cfrExtCircuitFECNOuts {
      type yang:counter32;
      description
       "Total number of frames sent out to the network 
        indicating forward congestion.";
      smiv2:max-access "read-only";
      smiv2:oid "1.3.6.1.4.1.9.9.49.1.2.2.1.11";
    }

    leaf cfrExtCircuitBECNOuts {
      type yang:counter32;
      description
       "Total number of frames sent out to the network 
        indicating backward congestion.";
      smiv2:max-access "read-only";
      smiv2:oid "1.3.6.1.4.1.9.9.49.1.2.2.1.12";
    }

    leaf cfrExtCircuitMinThruputOut {
      type int32 {
        range "9600..1544000";
      }
      units "bits per second";
      description
       "Circuit's outgoing minimal Throughput based on 
        configuration.";
      smiv2:max-access "read-only";
      smiv2:oid "1.3.6.1.4.1.9.9.49.1.2.2.1.13";
    }

    leaf cfrExtCircuitMinThruputIn {
      type int32 {
        range "9600..1544000";
      }
      units "bits per second";
      description
       "Circuit's incoming minimal Throughput based on
        configuration.";
      smiv2:max-access "read-only";
      smiv2:oid "1.3.6.1.4.1.9.9.49.1.2.2.1.14";
    }

    leaf cfrExtCircuitBcastPktOuts {
      type yang:counter32;
      description
       "Total number of broadcast packets sent out to the 
        network.";
      smiv2:max-access "read-only";
      smiv2:oid "1.3.6.1.4.1.9.9.49.1.2.2.1.15";
    }

    leaf cfrExtCircuitBcastByteOuts {
      type yang:counter32;
      description
       "Total number of bytes sent out to the network in 
        broadcast packets.";
      smiv2:max-access "read-only";
      smiv2:oid "1.3.6.1.4.1.9.9.49.1.2.2.1.16";
    }

    leaf cfrExtCircuitBandwidth {
      type int32 {
        range "0..16777215";
      }
      units "bits per second";
      description
       "Bandwidth of the virtual circuit, acquired from 
        Cisco typed LMI Full Status message.";
      smiv2:max-access "read-only";
      smiv2:oid "1.3.6.1.4.1.9.9.49.1.2.2.1.17";
    }

    leaf cfrExtCircuitShapeByteLimit {
      type int32 {
        range "125..2147483647";
      }
      units "octets";
      description
       "Maximum number of tokens a token bucket can hold in any
        time interval in case of traffic shaping.";
      smiv2:max-access "read-only";
      smiv2:oid "1.3.6.1.4.1.9.9.49.1.2.2.1.18";
    }

    leaf cfrExtCircuitShapeInterval {
      type int32 {
        range "10..125";
      }
      units "milliseconds";
      description
       "Committed rate measurement interval.";
      smiv2:max-access "read-only";
      smiv2:oid "1.3.6.1.4.1.9.9.49.1.2.2.1.19";
    }

    leaf cfrExtCircuitShapeByteIncrement {
      type int32 {
        range "125..2147483647";
      }
      units "octets";
      description
       "Number of tokens added into the token bucket per time
        interval in case of traffic shaping.";
      smiv2:max-access "read-only";
      smiv2:oid "1.3.6.1.4.1.9.9.49.1.2.2.1.20";
    }

    leaf cfrExtCircuitShapePkts {
      type yang:counter32;
      description
       "Total number of packets that went through traffic 
        shaping.";
      smiv2:max-access "read-only";
      smiv2:oid "1.3.6.1.4.1.9.9.49.1.2.2.1.21";
    }

    leaf cfrExtCircuitShapeBytes {
      type yang:counter32;
      units "octets";
      description
       "Total number of bytes that went through traffic 
        shaping.";
      smiv2:max-access "read-only";
      smiv2:oid "1.3.6.1.4.1.9.9.49.1.2.2.1.22";
    }

    leaf cfrExtCircuitShapePktsDelay {
      type yang:counter32;
      description
       "Total number of packets that were delayed by the 
        traffic shaper.";
      smiv2:max-access "read-only";
      smiv2:oid "1.3.6.1.4.1.9.9.49.1.2.2.1.23";
    }

    leaf cfrExtCircuitShapeBytesDelay {
      type yang:counter32;
      units "octets";
      description
       "Total number of bytes that were delayed by the 
        traffic shaper.";
      smiv2:max-access "read-only";
      smiv2:oid "1.3.6.1.4.1.9.9.49.1.2.2.1.24";
    }

    leaf cfrExtCircuitShapeActive {
      type boolean;
      description
       "Shows whether shaping is active or not.";
      smiv2:max-access "read-only";
      smiv2:oid "1.3.6.1.4.1.9.9.49.1.2.2.1.25";
    }

    leaf cfrExtCircuitShapeAdapting {
      type enumeration {
        enum "none" {
          value "1";
        }
        enum "becn" {
          value "2";
        }
        enum "foreSight" {
          value "3";
        }
      }
      description
       "Type of Adaptive Shaping configured.
        none(1)      - No adaptive shaping configured
        becn(2)      - Backward Explicit Congestion Notification
        foreSight(3) - ForeSight is the network traffic control 
                       software used in Cisco WAN switches";
      smiv2:max-access "read-only";
      smiv2:oid "1.3.6.1.4.1.9.9.49.1.2.2.1.26";
    }

    leaf cfrExtCircuitTxDataRate {
      type int32 {
        range "1..45000000";
      }
      description
       "The average rate (bytes/second) at which data is 
        transmitted in this circuit. ";
      smiv2:max-access "read-only";
      smiv2:oid "1.3.6.1.4.1.9.9.49.1.2.2.1.27";
    }

    leaf cfrExtCircuitTxPktRate {
      type int32 {
        range "1..45000000";
      }
      description
       "The average number of packets sent in a second in this 
        circuit.";
      smiv2:max-access "read-only";
      smiv2:oid "1.3.6.1.4.1.9.9.49.1.2.2.1.28";
    }

    leaf cfrExtCircuitRcvDataRate {
      type int32 {
        range "1..45000000";
      }
      description
       "The average rate (bytes/second) at which data is 
        received in this circuit. ";
      smiv2:max-access "read-only";
      smiv2:oid "1.3.6.1.4.1.9.9.49.1.2.2.1.29";
    }

    leaf cfrExtCircuitRcvPktRate {
      type int32 {
        range "1..45000000";
      }
      description
       "The average number of packets received in a second in 
        this circuit. ";
      smiv2:max-access "read-only";
      smiv2:oid "1.3.6.1.4.1.9.9.49.1.2.2.1.30";
    }
  }

  smiv2:alias "ciscoFrameRelayMIB" {
    smiv2:oid "1.3.6.1.4.1.9.9.49";
  }

  smiv2:alias "ciscoFrMIBObjects" {
    smiv2:oid "1.3.6.1.4.1.9.9.49.1";
  }

  smiv2:alias "cfrLmiObjs" {
    smiv2:oid "1.3.6.1.4.1.9.9.49.1.1";
  }

  smiv2:alias "cfrCircuitObjs" {
    smiv2:oid "1.3.6.1.4.1.9.9.49.1.2";
  }

  smiv2:alias "cfrMapObjs" {
    smiv2:oid "1.3.6.1.4.1.9.9.49.1.3";
  }

  smiv2:alias "cfrSvcObjs" {
    smiv2:oid "1.3.6.1.4.1.9.9.49.1.4";
  }

  smiv2:alias "cfrElmiObjs" {
    smiv2:oid "1.3.6.1.4.1.9.9.49.1.5";
  }

  smiv2:alias "cfrFragObjs" {
    smiv2:oid "1.3.6.1.4.1.9.9.49.1.6";
  }

  smiv2:alias "cfrConnectionObjs" {
    smiv2:oid "1.3.6.1.4.1.9.9.49.1.7";
  }

  smiv2:alias "ciscoFrMIBConformance" {
    smiv2:oid "1.3.6.1.4.1.9.9.49.3";
  }

  smiv2:alias "ciscoFrMIBCompliances" {
    smiv2:oid "1.3.6.1.4.1.9.9.49.3.1";
  }

  smiv2:alias "ciscoFrMIBGroups" {
    smiv2:oid "1.3.6.1.4.1.9.9.49.3.2";
  }

}
