/*
 * Generated by confdc --mib2yang-std
 * Source: /Users/janl/git/cia/capp/NetworkElementSynchronizer/../../mibs/mib-source/RFC1155-SMI.mib
 */
/*
 * This YANG module has been generated by smidump 0.5.0:
 *
 *      smidump -f yang RFC1155-SMI
 *
 * Do not edit. Edit the source file instead!
 */

module RFC1155-SMI {

  namespace "urn:ietf:params:xml:ns:yang:smiv2:RFC1155-SMI";
  prefix "rfc1155-smi";

  import ietf-yang-smiv2 {
    prefix "smiv2";
  }

  import ietf-yang-types {
    prefix "yang";
  }

  import ietf-inet-types { prefix inet; }

  typedef ObjectName {
    type yang:object-identifier-128;
  }

  typedef NetworkAddress {
    type inet:ipv4-address;
  }

  typedef IpAddress {
    type binary {
      length "4";
    }
  }

  typedef Counter {
    type uint32 {
      range "0..4294967295";
    }
  }

  typedef Gauge {
    type uint32 {
      range "0..4294967295";
    }
  }

  typedef TimeTicks {
    type uint32 {
      range "0..4294967295";
    }
  }

  typedef Opaque {
    type binary;
  }

  smiv2:alias "internet" {
    smiv2:oid "1.3.6.1";
  }

  smiv2:alias "directory" {
    smiv2:oid "1.3.6.1.1";
  }

  smiv2:alias "mgmt" {
    smiv2:oid "1.3.6.1.2";
  }

  smiv2:alias "experimental" {
    smiv2:oid "1.3.6.1.3";
  }

  smiv2:alias "private" {
    smiv2:oid "1.3.6.1.4";
  }

  smiv2:alias "enterprises" {
    smiv2:oid "1.3.6.1.4.1";
  }

}
