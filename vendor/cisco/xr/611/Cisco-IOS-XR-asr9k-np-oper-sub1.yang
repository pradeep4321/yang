submodule Cisco-IOS-XR-asr9k-np-oper-sub1 {

  belongs-to Cisco-IOS-XR-asr9k-np-oper {
    prefix Cisco-IOS-XR-asr9k-np-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR asr9k-np package operational data.

     Copyright (c) 2013-2016 by Cisco Systems, Inc.
     All rights reserved.";

  revision "2015-11-09" {
    description
      "IOS XR 6.0 revision.";
  }


  grouping PRM-NP-FAST-DROP-A {
    description "NP fast drop";
    leaf interface-name {
      xr:xr-xml-map "prm_np_edm_defs:InterfaceName";
      type string;
      description "Interface name";
    }
    leaf counter-value {
      xr:xr-xml-map "prm_np_edm_defs:CounterValue";
      type uint64;
      description "The Value of the counter";
    }
  }

  grouping PRM-NP-FAST-DROP {
    description "Array of NP Fast Drop Counters";

    list np-fast-drop {
      description "Array of NP Fast Drop Counters";
      uses PRM-NP-FAST-DROP-A;
    }
  }

  grouping PRM-NP-COUNTERS-A {
    description "NP Counters";
    leaf counter-index {
      xr:xr-xml-map "prm_np_edm_defs:CounterIndex";
      type uint32;
      description "Counter Index";
    }
    leaf counter-value {
      xr:xr-xml-map "prm_np_edm_defs:CounterValue";
      type uint64;
      description "The accurate value of the counter";
    }
    leaf rate {
      xr:xr-xml-map "prm_np_edm_defs:Rate";
      type uint32;
      units "packet/s";
      description "Rate in Packets Per Second";
    }
    leaf counter-type {
      xr:xr-xml-map "prm_np_edm_defs:CounterType";
      type string;
      description
        "Counter TypeDROP: Drop counterPUNT: Punt
        counterFWD:  Forward or generic counterUNKNOWN:
        Counter type unknown";
    }
    leaf counter-name {
      xr:xr-xml-map "prm_np_edm_defs:CounterName";
      type string;
      description "Counter name";
    }
  }

  grouping PRM-NP-COUNTERS {
    description "Array of NP Counters";

    list np-counter {
      description "Array of NP Counters";
      uses PRM-NP-COUNTERS-A;
    }
  }

  grouping TCAM-VMR-ENTRY {
    description "application vmr entry";
    leaf num-vmr-ids {
      xr:xr-xml-map "prm_np_edm_defs:NumVmrIds";
      type uint32;
      description "Vmr IDs";
    }
    leaf num-active-entries {
      xr:xr-xml-map "prm_np_edm_defs:NumActiveEntries";
      type uint32;
      description "The number of active vmr entries";
    }
    leaf num-allocated-entries {
      xr:xr-xml-map "prm_np_edm_defs:NumAllocatedEntries";
      type uint32;
      description "The number of active vmr entries";
    }
  }

  grouping ACL-COMM-REGION {
    description "acl common region";
    leaf free-entries {
      xr:xr-xml-map "prm_np_edm_defs:FreeEntries";
      type uint32;
      description "Free entries in the table";
    }
    leaf allocated-entries {
      xr:xr-xml-map "prm_np_edm_defs:AllocatedEntries";
      type uint32;
      description "The number of active vmr entries";
    }
  }

  grouping TCAM-ODS-TABLE {
    description "tcam ods table";

    container acl-common {
      description "ACL common region";
      uses ACL-COMM-REGION;
    }

    container app-id-ifib {
      description "app IFIB entry";
      uses TCAM-VMR-ENTRY;
    }

    container app-id-qos {
      description "app qos entry";
      uses TCAM-VMR-ENTRY;
    }

    container app-id-acl {
      description "app acl entry";
      uses TCAM-VMR-ENTRY;
    }

    container app-id-afmon {
      description "app afmon entry";
      uses TCAM-VMR-ENTRY;
    }

    container app-id-li {
      description "app LI entry";
      uses TCAM-VMR-ENTRY;
    }

    container app-id-pbr {
      description "app PBR entry";
      uses TCAM-VMR-ENTRY;
    }

    container app-id-edpl {
      description "app EDPL entry";
      uses TCAM-VMR-ENTRY;
    }
    leaf free-entries {
      xr:xr-xml-map "prm_np_edm_defs:FreeEntries";
      type uint32;
      description "Free entries in the table";
    }
    leaf reserved-entries {
      xr:xr-xml-map "prm_np_edm_defs:ReservedEntries";
      type uint32;
      description "The number of active vmr entries";
    }
  }

  grouping TCAM-L2-TABLE {
    description "tcam l2 table";
    leaf partition-id {
      xr:xr-xml-map "prm_np_edm_defs:PartitionID";
      type uint32;
      description "PartitionID";
    }
    leaf priority {
      xr:xr-xml-map "prm_np_edm_defs:Priority";
      type uint32;
      description "Priority";
    }
    leaf valid-entries {
      xr:xr-xml-map "prm_np_edm_defs:ValidEntries";
      type uint32;
      description "Valid Entries";
    }
    leaf free-entries {
      xr:xr-xml-map "prm_np_edm_defs:FreeEntries";
      type uint32;
      description "Free Entries";
    }
  }

  grouping TCAM-SHOW-SUM {
    description "tcam summary";

    container tcam-lt-l2 {
      description "TCAM L2 partition summary";
      uses TCAM-L2-TABLE;
    }

    container tcam-lt-ods2 {
      description "TCAM ODS2 partition summary";
      uses TCAM-ODS-TABLE;
    }

    container tcam-lt-ods8 {
      description "TCAM ODS8 partition summary";
      uses TCAM-ODS-TABLE;
    }
  }

  grouping TCAM-VMR-ENTRY-INT {
    description "application vmr entry internal";
    leaf num-vmr-ids {
      xr:xr-xml-map "prm_np_edm_defs:NumVmrIds";
      type uint32;
      description "Vmr IDs";
    }
    leaf total-used-entries {
      xr:xr-xml-map "prm_np_edm_defs:TotalUsedEntries";
      type uint32;
      description "number of used vmr entries";
    }
    leaf total-allocated-entries {
      xr:xr-xml-map "prm_np_edm_defs:TotalAllocatedEntries";
      type uint32;
      description "The number of active vmr entries";
    }
  }

  grouping TCAM-ODS-TABLE-INT {
    description "tcam ods table internal";

    container app-id-ifib {
      description "app IFIB entry";
      uses TCAM-VMR-ENTRY-INT;
    }

    container app-id-qos {
      description "app qos entry";
      uses TCAM-VMR-ENTRY-INT;
    }

    container app-id-acl {
      description "app acl entry";
      uses TCAM-VMR-ENTRY-INT;
    }

    container app-id-afmon {
      description "app afmon entry";
      uses TCAM-VMR-ENTRY-INT;
    }

    container app-id-li {
      description "app LI entry";
      uses TCAM-VMR-ENTRY-INT;
    }

    container app-id-pbr {
      description "app PBR entry";
      uses TCAM-VMR-ENTRY-INT;
    }

    container application-edpl-entry {
      description "app EDPL entry";
      uses TCAM-VMR-ENTRY-INT;
    }
    leaf max-entries {
      xr:xr-xml-map "prm_np_edm_defs:MaxEntries";
      type uint32;
      description "Max entries";
    }
    leaf free-entries {
      xr:xr-xml-map "prm_np_edm_defs:FreeEntries";
      type uint32;
      description "free entries";
    }
  }

  grouping TCAM-L2-TABLE-INT {
    description "tcam l2 table internal";
    leaf partition-id {
      xr:xr-xml-map "prm_np_edm_defs:PartitionID";
      type uint32;
      description "PartitionID";
    }
    leaf valid-entries {
      xr:xr-xml-map "prm_np_edm_defs:ValidEntries";
      type uint32;
      description "Valid Entries";
    }
    leaf free-entries {
      xr:xr-xml-map "prm_np_edm_defs:FreeEntries";
      type uint32;
      description "Free Entries";
    }
  }

  grouping TCAM-SHOW-SUM-INT {
    description "tcam summary internal";

    container tcam-lt-l2 {
      description "TCAM LT L2 summary";
      uses TCAM-L2-TABLE-INT;
    }

    container tcam-lt-ods2 {
      description "TCAM LT ODS 2 summary";
      uses TCAM-ODS-TABLE-INT;
    }

    container tcam-lt-ods8 {
      description "TCAM LT_ODS 8 summary";
      uses TCAM-ODS-TABLE-INT;
    }
  }

  grouping TCAM-INFO-SHOW-SUM {
    description "tcam summary info";

    container internal-tcam-info {
      description "Internal tcam summary info";
      uses TCAM-SHOW-SUM-INT;
    }

    container tcam-info {
      description "External tcam summary info";
      uses TCAM-SHOW-SUM;
    }
  }

  grouping PRM-NP-CHN-LOAD-A {
    description "NP Channel load counters";
    leaf flow-ctr-counter {
      xr:xr-xml-map "prm_np_edm_defs:FlowCtrCounter";
      type uint32;
      description "Flow control counters";
    }
    leaf avg-rfd-usage {
      xr:xr-xml-map "prm_np_edm_defs:AvgRFDUsage";
      type uint32;
      description "Average RFD Usage";
    }
    leaf peak-rfd-usage {
      xr:xr-xml-map "prm_np_edm_defs:PeakRFDUsage";
      type uint32;
      description "Peak RFD Usage";
    }
    leaf avg-guar-rfd-usage {
      xr:xr-xml-map "prm_np_edm_defs:AvgGuarRFDUsage";
      type uint32;
      description "Average of garanteed RFD usage";
    }
    leaf peak-guar-rfd-usage {
      xr:xr-xml-map "prm_np_edm_defs:PeakGuarRFDUsage";
      type uint32;
      description "Peak of garanteed RFD usage";
    }
    leaf interface-name {
      xr:xr-xml-map "prm_np_edm_defs:InterfaceName";
      type string;
      description "Inerface Name";
    }
  }

  grouping PRM-NP-CHN-LOAD {
    description "Array of NP Channel load counters";

    list np-chn-load {
      description "Array of NP Channel load counters";
      uses PRM-NP-CHN-LOAD-A;
    }
  }
}
