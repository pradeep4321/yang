module Cisco-IOS-XR-cfgmgr-rollback-act {

    namespace "http://cisco.com/ns/yang/Cisco-IOS-XR-cfgmgr-rollback-act";
    
    prefix "rollback-act";
    
    import Cisco-IOS-XR-sch-types { prefix "csc"; }
    
    organization "Cisco Systems, Inc.";
    
    contact
    "Cisco Systems, Inc.
     Customer Service

     Postal: 170 West Tasman Drive
     San Jose, CA 95134

     Tel: +1 800 553-NETS

     E-mail: cs-yang@cisco.com";
    
    description 
    "This module contains a collection of YANG definitions
     for Cisco IOS-XR action package configuration.

     Copyright (c) 2016 by Cisco Systems, Inc.
     All rights reserved.";
    
    revision "2016-04-17" {
        description
            "IOS XR 6.1.1 revision.";
    }

    grouping ROLLBACK-ATTRIBUTES {
        leaf force {
            when "../best-effort = 'false'" {
                description "Only when best-effort is false.";
            }
            description "Override commit blocks";
            type boolean;
            default "false";
        }
        leaf best-effort {
            when "../force = 'false'" {
                description "Only when force is false.";
            }
            description "Rollback via best-effort operation";
            type boolean;
            default "false";
        }
        leaf label {
            description "Assign a label to this rollback";
            type string;
        }
        leaf comment {
            description "Assign a comment to this rollback";
            type string;
        }
    }

    rpc roll-back-configuration-last {
        description "Rollback last <n> commits made";
        csc:xr-task "root-system";
        input {
            leaf count {
                description "Number of commits to rollback";
                type int32 {
                    range "1..100";
                }
                mandatory true;
            }
            uses ROLLBACK-ATTRIBUTES;
        }
    }

    rpc roll-back-configuration-to {
        description "Rollback up to (and including) a specific commit";
        csc:xr-task "root-system";
        input {
            leaf commit-id {
                description "Commit ID";
                type string;
                mandatory true;
            }
            uses ROLLBACK-ATTRIBUTES;
        }
    }

    rpc roll-back-configuration-to-exclude {
        description "Rollback up to (and excluding) a specific commit";
        csc:xr-task "root-system";
        input {
            leaf commit-id {
                description "Commit ID";
                type string;
                mandatory true;
            }
            uses ROLLBACK-ATTRIBUTES;
        }
    }

    rpc roll-back-configuration {
        description "Rollback a specific commit";
        csc:xr-task "root-system";
        input {
            leaf commit-id {
                description "Commit ID";
                type string;
                mandatory true;
            }
            uses ROLLBACK-ATTRIBUTES;
        }
    }
}
