module Cisco-IOS-XR-clns-isis-cfg {

  /*** NAMESPACE / PREFIX DEFINITION ***/

  namespace "http://cisco.com/ns/yang/Cisco-IOS-XR-clns-isis-cfg";


  prefix "clns-isis-cfg";

  /*** LINKAGE (IMPORTS / INCLUDES) ***/

  import ietf-inet-types { prefix "inet"; }

  import Cisco-IOS-XR-types { prefix "xr"; }

  import Cisco-IOS-XR-clns-isis-datatypes { prefix "dt1"; }

  import Cisco-IOS-XR-snmp-agent-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR clns-isis package configuration.

     This module contains definitions
     for the following management objects:
       isis: IS-IS configuration for all instances

     This YANG module augments the
       Cisco-IOS-XR-snmp-agent-cfg
     module with configuration data.

     Copyright (c) 2013-2016 by Cisco Systems, Inc.
     All rights reserved.";

  revision "2015-11-09" {
    description
      "IOS XR 6.0 revision.";
  }

  typedef Isis-mib-manual-address-drops-boolean {
    type enumeration {
      enum false {
        value 0;
        description "Disable";
      }
      enum true {
        value 2;
        description "Enable";
      }
    }
    description "Isis mib manual address drops boolean";
  }
  typedef Nflag-clear {
    type enumeration {
      enum disable {
        value 0;
        description "Disable N-flag-clear";
      }
      enum enable {
        value 1;
        description "Enable N-flag-clear";
      }
    }
    description "Nflag clear";
  }
  typedef Isis-adv-type-inter-level {
    type enumeration {
      enum inter-level {
        value 1;
        description "InterLevel";
      }
    }
    description "Isis adv type inter level";
  }
  typedef Isis-mib-authentication-type-failure-boolean {
    type enumeration {
      enum false {
        value 0;
        description "Disable";
      }
      enum true {
        value 9;
        description "Enable";
      }
    }
    description "Isis mib authentication type failure boolean";
  }
  typedef Isis-interface-state {
    type enumeration {
      enum shutdown {
        value 0;
        description "Shutdown";
      }
      enum suppressed {
        value 1;
        description "Suppressed";
      }
      enum passive {
        value 2;
        description "Passive";
      }
    }
    description "Isis interface state";
  }
  typedef Isisfrr {
    type enumeration {
      enum per-link {
        value 1;
        description "Prefix independent per-link computation";
      }
      enum per-prefix {
        value 2;
        description "Prefix dependent computation";
      }
    }
    description "Isisfrr";
  }
  typedef Isisfrr-load-sharing {
    type enumeration {
      enum disable {
        value 1;
        description
          "Disable load sharing of prefixes across
          multiple backups";
      }
    }
    description "Isisfrr load sharing";
  }
  typedef Isis-authentication-failure-mode {
    type enumeration {
      enum drop {
        value 0;
        description "Drop non-authenticating PDUs";
      }
      enum send-only {
        value 1;
        description "Accept non-authenticating PDUs";
      }
    }
    description "Isis authentication failure mode";
  }
  typedef Isis-apply-weight {
    type enumeration {
      enum ecmp-only {
        value 1;
        description "Apply weight to ECMP prefixes";
      }
      enum ucmp-only {
        value 2;
        description "Apply weight to UCMP prefixes";
      }
    }
    description "Isis apply weight";
  }
  typedef Isis-label-preference {
    type enumeration {
      enum ldp {
        value 0;
        description "Label Distribution Protocol";
      }
      enum segment-routing {
        value 1;
        description "Segment Routing";
      }
    }
    description "Isis label preference";
  }
  typedef Isis-mib-max-area-address-mismatch-boolean {
    type enumeration {
      enum false {
        value 0;
        description "Disable";
      }
      enum true {
        value 6;
        description "Enable";
      }
    }
    description "Isis mib max area address mismatch boolean";
  }
  typedef Isis-metric-style-transition {
    type enumeration {
      enum disabled {
        value 0;
        description "Disabled";
      }
      enum enabled {
        value 1;
        description "Enabled";
      }
    }
    description "Isis metric style transition";
  }
  typedef Isis-mib-sequence-number-skip-boolean {
    type enumeration {
      enum false {
        value 0;
        description "Disable";
      }
      enum true {
        value 8;
        description "Enable";
      }
    }
    description "Isis mib sequence number skip boolean";
  }
  typedef Isissid {
    type enumeration {
      enum index {
        value 1;
        description "SID as an index";
      }
      enum absolute {
        value 2;
        description "SID as an absolute label";
      }
    }
    description "Isissid";
  }
  typedef Isis-metric {
    type enumeration {
      enum internal {
        value 0;
        description "Internal metric";
      }
      enum external {
        value 1;
        description "External metric";
      }
    }
    description "Isis metric";
  }
  typedef Isis-mib-database-over-flow-boolean {
    type enumeration {
      enum false {
        value 0;
        description "Disable";
      }
      enum true {
        value 1;
        description "Enable";
      }
    }
    description "Isis mib database over flow boolean";
  }
  typedef Isis-mib-all-boolean {
    type enumeration {
      enum false {
        value 0;
        description "Disable";
      }
      enum true {
        value 19;
        description "Enable";
      }
    }
    description "Isis mib all boolean";
  }
  typedef Isis-attached-bit {
    type enumeration {
      enum area {
        value 0;
        description "Computed from the attached areas";
      }
      enum on {
        value 1;
        description "Forced ON";
      }
      enum off {
        value 2;
        description "Forced OFF";
      }
    }
    description "Isis attached bit";
  }
  typedef Isis-configurable-levels {
    type enumeration {
      enum level1 {
        value 1;
        description "Level1";
      }
      enum level2 {
        value 2;
        description "Level2";
      }
      enum level1-and2 {
        value 3;
        description "Both Levels";
      }
    }
    description "Isis configurable levels";
  }
  typedef Isis-mib-lsp-too-large-to-propagate-boolean {
    type enumeration {
      enum false {
        value 0;
        description "Disable";
      }
      enum true {
        value 14;
        description "Enable";
      }
    }
    description "Isis mib lsp too large to propagate boolean";
  }
  typedef Isis-mib-own-lsp-purge-boolean {
    type enumeration {
      enum false {
        value 0;
        description "Disable";
      }
      enum true {
        value 7;
        description "Enable";
      }
    }
    description "Isis mib own lsp purge boolean";
  }
  typedef Isis-hello-padding {
    type enumeration {
      enum never {
        value 0;
        description "Never pad Hellos";
      }
      enum sometimes {
        value 1;
        description "Pad Hellos during adjacency formation only";
      }
    }
    description "Isis hello padding";
  }
  typedef Isis-snp-auth {
    type enumeration {
      enum send-only {
        value 0;
        description "Authenticate SNP send only";
      }
      enum full {
        value 1;
        description "Authenticate SNP send and recv";
      }
    }
    description "Isis snp auth";
  }
  typedef Isis-interface-af-state {
    type enumeration {
      enum disable {
        value 0;
        description "Disable";
      }
    }
    description "Isis interface af state";
  }
  typedef Isisexplicit-null-flag {
    type enumeration {
      enum disable {
        value 0;
        description "Disable EXPLICITNULL";
      }
      enum enable {
        value 1;
        description "Enable EXPLICITNULL";
      }
    }
    description "Isisexplicit null flag";
  }
  typedef Isis-mib-adjacency-change-boolean {
    type enumeration {
      enum false {
        value 0;
        description "Disable";
      }
      enum true {
        value 17;
        description "Enable";
      }
    }
    description "Isis mib adjacency change boolean";
  }
  typedef Isis-mib-protocols-supported-mismatch-boolean {
    type enumeration {
      enum false {
        value 0;
        description "Disable";
      }
      enum true {
        value 16;
        description "Enable";
      }
    }
    description "Isis mib protocols supported mismatch boolean";
  }
  typedef Isis-mib-attempt-to-exceed-max-sequence-boolean {
    type enumeration {
      enum false {
        value 0;
        description "Disable";
      }
      enum true {
        value 4;
        description "Enable";
      }
    }
    description "Isis mib attempt to exceed max sequence boolean";
  }
  typedef Isis-redist-proto {
    type enumeration {
      enum connected {
        value 0;
        description "Connected";
      }
      enum static {
        value 1;
        description "Static";
      }
      enum ospf {
        value 2;
        description "OSPF";
      }
      enum bgp {
        value 3;
        description "BGP";
      }
      enum isis {
        value 4;
        description "ISIS";
      }
      enum ospfv3 {
        value 5;
        description "OSPFv3";
      }
      enum rip {
        value 6;
        description "RIP";
      }
      enum eigrp {
        value 7;
        description "EIGRP";
      }
      enum subscriber {
        value 8;
        description "Subscriber";
      }
      enum application {
        value 9;
        description "Application";
      }
      enum mobile {
        value 10;
        description "Mobile";
      }
    }
    description "Isis redist proto";
  }
  typedef Isis-tracing-mode {
    type enumeration {
      enum off {
        value 0;
        description "No tracing";
      }
      enum basic {
        value 1;
        description "Basic tracing (less overhead)";
      }
      enum enhanced {
        value 2;
        description "Enhanced tracing (more overhead)";
      }
    }
    description "Isis tracing mode";
  }
  typedef Isis-prefix-priority {
    type enumeration {
      enum critical-priority {
        value 0;
        description "Critical prefix priority";
      }
      enum high-priority {
        value 1;
        description "High prefix priority";
      }
      enum medium-priority {
        value 2;
        description "Medium prefix priority";
      }
    }
    description "Isis prefix priority";
  }
  typedef Isis-mib-id-length-mismatch-boolean {
    type enumeration {
      enum false {
        value 0;
        description "Disable";
      }
      enum true {
        value 5;
        description "Enable";
      }
    }
    description "Isis mib id length mismatch boolean";
  }
  typedef Isis-authentication-algorithm {
    type enumeration {
      enum cleartext {
        value 1;
        description "Cleartext password";
      }
      enum hmac-md5 {
        value 2;
        description "HMAC-MD5 checksum";
      }
      enum keychain {
        value 3;
        description "Key Chain authentication";
      }
    }
    description "Isis authentication algorithm";
  }
  typedef Isis-mib-originated-lsp-buffer-size-mismatch-boolean {
    type enumeration {
      enum false {
        value 0;
        description "Disable";
      }
      enum true {
        value 15;
        description "Enable";
      }
    }
    description
      "Isis mib originated lsp buffer size mismatch
      boolean";
  }
  typedef Isisispf-state {
    type enumeration {
      enum enabled {
        value 1;
        description "Enabled";
      }
    }
    description "Isisispf state";
  }
  typedef Isis-mib-area-mismatch-boolean {
    type enumeration {
      enum false {
        value 0;
        description "Disable";
      }
      enum true {
        value 12;
        description "Enable";
      }
    }
    description "Isis mib area mismatch boolean";
  }
  typedef Isis-mib-corrupted-lsp-detected-boolean {
    type enumeration {
      enum false {
        value 0;
        description "Disable";
      }
      enum true {
        value 3;
        description "Enable";
      }
    }
    description "Isis mib corrupted lsp detected boolean";
  }
  typedef Isis-mib-lsp-error-detected-boolean {
    type enumeration {
      enum false {
        value 0;
        description "Disable";
      }
      enum true {
        value 18;
        description "Enable";
      }
    }
    description "Isis mib lsp error detected boolean";
  }
  typedef Isis-adv-type-external {
    type enumeration {
      enum external {
        value 1;
        description "External";
      }
    }
    description "Isis adv type external";
  }
  typedef Isisphp-flag {
    type enumeration {
      enum enable {
        value 0;
        description "Enable PHP";
      }
      enum disable {
        value 1;
        description "Disable PHP";
      }
    }
    description "Isisphp flag";
  }
  typedef Isis-mib-rejected-adjacency-boolean {
    type enumeration {
      enum false {
        value 0;
        description "Disable";
      }
      enum true {
        value 13;
        description "Enable";
      }
    }
    description "Isis mib rejected adjacency boolean";
  }
  typedef Isis-metric-style {
    type enumeration {
      enum old-metric-style {
        value 0;
        description "ISO 10589 metric style (old-style)";
      }
      enum new-metric-style {
        value 1;
        description "32-bit metric style (new-style)";
      }
      enum both-metric-style {
        value 2;
        description "Both forms of metric style";
      }
    }
    description "Isis metric style";
  }
  typedef Isis-remote-lfa {
    type enumeration {
      enum remote-lfa-none {
        value 0;
        description "No remote LFA option set";
      }
      enum remote-lfa-tunnel-ldp {
        value 1;
        description "Construct remote LFA tunnel using MPLS LDP";
      }
    }
    description "Isis remote lfa";
  }
  typedef Isis-mib-version-skew-boolean {
    type enumeration {
      enum false {
        value 0;
        description "Disable";
      }
      enum true {
        value 11;
        description "Enable";
      }
    }
    description "Isis mib version skew boolean";
  }
  typedef Isis-mib-authentication-failure-boolean {
    type enumeration {
      enum false {
        value 0;
        description "Disable";
      }
      enum true {
        value 10;
        description "Enable";
      }
    }
    description "Isis mib authentication failure boolean";
  }
  typedef Isis-micro-loop-avoidance {
    type enumeration {
      enum not-set {
        value 0;
        description "No Avoidance type set";
      }
      enum micro-loop-avoidance-all {
        value 1;
        description "Provide mirco loop avoidance for all prefixes";
      }
      enum micro-loop-avoidance-protected {
        value 2;
        description
          "Provide mirco loop avoidance only for protected
          prefixes";
      }
    }
    description "Isis micro loop avoidance";
  }
  typedef Isis-adj-check {
    type enumeration {
      enum disabled {
        value 0;
        description "Disabled";
      }
    }
    description "Isis adj check";
  }
  typedef Isis-interface-frr-tiebreaker {
    type enumeration {
      enum node-protecting {
        value 3;
        description "Prefer node protecting backup path";
      }
      enum srlg-disjoint {
        value 6;
        description "Prefer SRLG disjoint backup path";
      }
    }
    description "Isis interface frr tiebreaker";
  }
  typedef Isis-overload-bit-mode {
    type enumeration {
      enum permanently-set {
        value 1;
        description "Set always";
      }
      enum startup-period {
        value 2;
        description "Set during the startup period";
      }
      enum wait-for-bgp {
        value 3;
        description "Set until BGP comverges";
      }
    }
    description "Isis overload bit mode";
  }
  typedef Isis-nsf-flavor {
    type enumeration {
      enum cisco-proprietary-nsf {
        value 1;
        description "Cisco proprietary NSF";
      }
      enum ietf-standard-nsf {
        value 2;
        description "IETF standard NSF";
      }
    }
    description "Isis nsf flavor";
  }
  typedef Isisfrr-tiebreaker {
    type enumeration {
      enum downstream {
        value 0;
        description "Prefer backup path via downstream node";
      }
      enum lc-disjoint {
        value 1;
        description "Prefer line card disjoint backup path";
      }
      enum lowest-backup-metric {
        value 2;
        description "Prefer backup path with lowest total metric";
      }
      enum node-protecting {
        value 3;
        description "Prefer node protecting backup path";
      }
      enum primary-path {
        value 4;
        description "Prefer backup path from ECMP set";
      }
      enum secondary-path {
        value 5;
        description "Prefer non-ECMP backup path";
      }
      enum srlg-disjoint {
        value 6;
        description "Prefer SRLG disjoint backup path";
      }
    }
    description "Isisfrr tiebreaker";
  }

  grouping METRIC-TABLE {
    description "Common node of interface-af, af";

    container metrics {
      xr:xr-xml-map "isis_cfg:MetricTable";
      description "Metric configuration";

      list metric {
        xr:xr-xml-map "isis_cfg:Metric";
        key "level";
        description
          "Metric configuration. Legal value depends on
          the metric-style specified for the topology. If
          the metric-style defined is narrow, then only a
          value between <1-63> is allowed and if the
          metric-style is defined as wide, then a value
          between <1-16777215> is allowed as the metric
          value.  All routers exclude links with the
          maximum wide metric (16777215) from their SPF";
        leaf level {
          xr:xr-xml-map "isis_cfg:Level";
          type dt1:Isis-internal-level;
          description "Level to which configuration applies";
        }
        leaf metric {
          xr:xr-xml-map "isis_cfg:Metric";
          type union {
            type enumeration {
              enum maximum {
                value 16777215;
                description
                  "Maximum wide metric.  All routers will
                  exclude this link from their SPF";
              }
            }
            type uint32 {
              range "1..16777215";
            }
          }
          mandatory true;
          description
            "Allowed metric: <1-63> for narrow,
            <1-16777215> for wide";
        }
      }
    }
  }

  grouping WEIGHT-TABLE {
    description "Common node of interface-af, af";

    container weights {
      xr:xr-xml-map "isis_cfg:WeightTable";
      description "Weight configuration";

      list weight {
        xr:xr-xml-map "isis_cfg:Weight";
        key "level";
        description
          "Weight configuration under interface for load
          balancing";
        leaf level {
          xr:xr-xml-map "isis_cfg:Level";
          type dt1:Isis-internal-level;
          description "Level to which configuration applies";
        }
        leaf weight {
          xr:xr-xml-map "isis_cfg:Weight";
          type uint32 {
            range "1..16777214";
          }
          mandatory true;
          description
            "Weight to be configured under interface for
            Load Balancing. Allowed weight: <1-16777215>";
        }
      }
    }
  }

  container isis {
    xr:xr-xml-map "isis_cfg:ISIS";
    description "IS-IS configuration for all instances";

    container instances {
      xr:xr-xml-map "isis_cfg:InstanceTable";
      description "IS-IS instance configuration";

      list instance {
        xr:xr-xml-map "isis_cfg:Instance";
        key "instance-name";
        description "Configuration for a single IS-IS instance";

        container srgb {
          xr:xr-xml-map "isis_cfg:SRGB";
          presence "Indicates a srgb node is configured.";
          description "Segment Routing Global Block configuration";
          leaf lower-bound {
            xr:xr-xml-map "isis_cfg:LowerBound";
            type uint32 {
              range "16000..1048574";
            }
            mandatory true;
            description "The lower bound of the SRGB";
          }
          leaf upper-bound {
            xr:xr-xml-map "isis_cfg:UpperBound";
            type uint32 {
              range "16001..1048575";
            }
            mandatory true;
            description "The upper bound of the SRGB";
          }
        }

        container lsp-generation-intervals {
          xr:xr-xml-map "isis_cfg:LSPGenerationIntervalTable";
          description "LSP generation-interval configuration";

          list lsp-generation-interval {
            xr:xr-xml-map "isis_cfg:LSPGenerationInterval";
            xr:xr-cli-map "isis <string> lsp-gen-interval (0)|(1)|("+
              "2)|(3)|(4)|(5)|(6)|(7)|(8)|(9)|(10)|(11)|(12)|(13)|("+
              "14)|(15)|(16)|(17)|(18)|(19)|(20)|(21)|(22)|(23)|(24"+
              ")|(25)|(26)|(27)|(28)|(29)|(30)|(31)|(32)|(33)|(34)|"+
              "(35)|(36)|(37)|(38)|(39)|(40)|(41)|(42)|(43)|(44)|(4"+
              "5)|(46)|(47)|(48)|(49)|(50)|(51)|(52)|(53)|(54)|(55)"+
              "|(56)|(57)|(58)|(59)|(60)|(61)|(62)|(63)|(64)|(65)|("+
              "66)|(67)|(68)|(69)|(70)|(71)|(72)|(73)|(74)|(75)|(76"+
              ")|(77)|(78)|(79)|(80)|(81)|(82)|(83)|(84)|(85)|(86)|"+
              "(87)|(88)|(89)|(90)|(91)|(92)|(93)|(94)|(95)|(96)|(9"+
              "7)|(98)|(99)|(100)|(101)|(102)|(103)|(104)|(105)|(10"+
              "6)|(107)|(108)|(109)|(110)|(111)|(112)|(113)|(114)|("+
              "115)|(116)|(117)|(118)|(119)|(120) [level <number>] ";
            key "level";
            description "LSP generation scheduling parameters";
            leaf level {
              xr:xr-xml-map "isis_cfg:Level";
              type dt1:Isis-internal-level;
              description "Level to which configuration applies";
            }
            leaf maximum-wait {
              xr:xr-xml-map "isis_cfg:MaximumWait";
              type uint32 {
                range "0..120000";
              }
              units "millisecond";
              description
                "Maximum wait before generating local LSP in
                milliseconds";
            }
            leaf initial-wait {
              xr:xr-xml-map "isis_cfg:InitialWait";
              type uint32 {
                range "0..120000";
              }
              units "millisecond";
              description
                "Initial wait before generating local LSP in
                milliseconds";
            }
            leaf secondary-wait {
              xr:xr-xml-map "isis_cfg:SecondaryWait";
              type uint32 {
                range "0..120000";
              }
              units "millisecond";
              description
                "Secondary wait before generating local LSP
                in milliseconds";
            }
          }
        }

        container lsp-arrival-times {
          xr:xr-xml-map "isis_cfg:LSPArrivalTimeTable";
          description "LSP arrival time configuration";

          list lsp-arrival-time {
            xr:xr-xml-map "isis_cfg:LSPArrivalTime";
            xr:xr-cli-map "isis <string> min-lsp-arrivaltime (maxim"+
              "um-wait <number>)|(initial-wait <number>)|(secondary"+
              "-wait <number>) [level <number>] ";
            key "level";
            description "Minimum LSP arrival time";
            leaf level {
              xr:xr-xml-map "isis_cfg:Level";
              type dt1:Isis-internal-level;
              description "Level to which configuration applies";
            }
            leaf maximum-wait {
              xr:xr-xml-map "isis_cfg:MaximumWait";
              type uint32 {
                range "0..120000";
              }
              units "millisecond";
              description
                "Maximum delay expected to take since last
                LSPin milliseconds";
            }
            leaf initial-wait {
              xr:xr-xml-map "isis_cfg:InitialWait";
              type uint32 {
                range "0..120000";
              }
              units "millisecond";
              description
                "Initial delay expected to take since last
                LSPin milliseconds";
            }
            leaf secondary-wait {
              xr:xr-xml-map "isis_cfg:SecondaryWait";
              type uint32 {
                range "0..120000";
              }
              units "millisecond";
              description
                "Secondary delay expected to take since last
                LSPin milliseconds";
            }
          }
        }

        container trace-buffer-size {
          xr:xr-xml-map "isis_cfg:TraceBufferSize";
          description "Trace buffer size configuration";
          leaf detailed {
            xr:xr-xml-map "isis_cfg:Detailed";
            type uint32 {
              range "1..1000000";
            }
            description "Buffer size for detailed traces";
          }
          leaf standard {
            xr:xr-xml-map "isis_cfg:Standard";
            type uint32 {
              range "1..1000000";
            }
            description "Buffer size for standard traces";
          }
          leaf severe {
            xr:xr-xml-map "isis_cfg:Severe";
            type uint32 {
              range "1..1000000";
            }
            description "Buffer size for severe trace";
          }
          leaf hello {
            xr:xr-xml-map "isis_cfg:Hello";
            type uint32 {
              range "1..1000000";
            }
            description "Buffer size for hello trace";
          }
        }

        container max-link-metrics {
          xr:xr-xml-map "isis_cfg:MaxLinkMetricTable";
          description "Max Link Metric configuration";

          list max-link-metric {
            xr:xr-xml-map "isis_cfg:MaxLinkMetric";
            xr:xr-cli-map "isis <string> max-link-metric [level <nu"+
              "mber>] ";
            key "level";
            description "Max Link Metric";
            leaf level {
              xr:xr-xml-map "isis_cfg:Level";
              type dt1:Isis-internal-level;
              description "Level to which configuration applies";
            }
          }
        }

        container afs {
          xr:xr-xml-map "isis_cfg:AFTable";
          description "Per-address-family configuration";

          list af {
            must "af-data or topology-name" {
              description
                "af-data or topology-name must be present.";
            }
            key "saf-name af-name";
            description
              "Configuration for an IS-IS address-family. If
              a named (non-default) topology is being
              created it must be multicast.";

            grouping AF-CONTENT {
              description "Content grouping.";

              container segment-routing {
                xr:xr-xml-map "isis_cfg:SegmentRouting";
                description "Enable Segment Routing configuration";

                container prefix-sid-map {
                  xr:xr-xml-map "isis_cfg:PrefixSIDMap";
                  description
                    "Enable Segment Routing prefix SID map
                    configuration";
                  leaf advertise-local {
                    xr:xr-xml-map "isis_cfg:AdvertiseLocal";
                    type empty;
                    description
                      "Enable Segment Routing prefix SID map
                      advertise local";
                  }
                  leaf receive {
                    xr:xr-xml-map "isis_cfg:Receive";
                    type boolean;
                    description
                      "If TRUE, remote prefix SID map
                      advertisements will be used. If FALSE,
                      they will not be used.";
                  }
                }
                leaf mpls {
                  xr:xr-xml-map "isis_cfg:MPLS";
                  type Isis-label-preference;
                  description
                    "Prefer segment routing labels over LDP
                    labels";
                }
              }

              container metric-styles {
                xr:xr-xml-map "isis_cfg:MetricStyleTable";
                description "Metric-style configuration";

                list metric-style {
                  xr:xr-xml-map "isis_cfg:MetricStyle";
                  key "level";
                  description
                    "Configuration of metric style in LSPs";
                  leaf level {
                    xr:xr-xml-map "isis_cfg:Level";
                    type dt1:Isis-internal-level;
                    description
                      "Level to which configuration applies";
                  }
                  leaf style {
                    xr:xr-xml-map "isis_cfg:Style";
                    type Isis-metric-style;
                    default "old-metric-style";
                    description "Metric Style";
                  }
                  leaf transition-state {
                    xr:xr-xml-map "isis_cfg:TransitionState";
                    when "../style != 'both-metric-style'" {
                      description "../Style != 2";
                    }
                    type Isis-metric-style-transition;
                    default "disabled";
                    description "Transition state";
                  }
                }
              }

              container frr-table {
                xr:xr-xml-map "isis_cfg:FRRTable";
                description "Fast-ReRoute configuration";

                container frr-load-sharings {
                  xr:xr-xml-map "isis_cfg:FRRLoadSharingTable";
                  description
                    "Load share prefixes across multiple
                    backups";

                  list frr-load-sharing {
                    xr:xr-xml-map "isis_cfg:FRRLoadSharing";
                    key "level";
                    description "Disable load sharing";
                    leaf level {
                      xr:xr-xml-map "isis_cfg:Level";
                      type dt1:Isis-internal-level;
                      description
                        "Level to which configuration applies";
                    }
                    leaf load-sharing {
                      xr:xr-xml-map "isis_cfg:LoadSharing";
                      type Isisfrr-load-sharing;
                      mandatory true;
                      description "Load sharing";
                    }
                  }
                }

                container priority-limits {
                  xr:xr-xml-map "isis_cfg:FRRPriorityLimitTable";
                  description "FRR prefix-limit configuration";

                  list priority-limit {
                    xr:xr-xml-map "isis_cfg:PriorityLimit";
                    key "level frr-type";
                    description
                      "Limit backup computation upto the prefix
                      priority";
                    leaf level {
                      xr:xr-xml-map "isis_cfg:Level";
                      type dt1:Isis-internal-level;
                      description
                        "Level to which configuration applies";
                    }
                    leaf frr-type {
                      xr:xr-xml-map "isis_cfg:FRRType";
                      type Isisfrr;
                      description "Computation Type";
                    }
                    leaf priority {
                      xr:xr-xml-map "isis_cfg:Priority";
                      type Isis-prefix-priority;
                      mandatory true;
                      description
                        "Compute for all prefixes upto the
                        specified priority";
                    }
                  }
                }

                container frr-remote-lfa-prefixes {
                  xr:xr-xml-map "isis_cfg:FRRRemoteLFAPrefixListTab"+
                    "le";
                  description
                    "FRR remote LFA prefix list filter
                    configuration";

                  list frr-remote-lfa-prefix {
                    xr:xr-xml-map "isis_cfg:FRRRemoteLFAPrefixList";
                    key "level";
                    description
                      "Filter remote LFA router IDs using
                      prefix-list";
                    leaf level {
                      xr:xr-xml-map "isis_cfg:Level";
                      type dt1:Isis-internal-level;
                      description
                        "Level to which configuration applies";
                    }
                    leaf prefix-list-name {
                      xr:xr-xml-map "isis_cfg:PrefixListName";
                      type string;
                      mandatory true;
                      description "Name of the prefix list";
                    }
                  }
                }

                container frr-tiebreakers {
                  xr:xr-xml-map "isis_cfg:FRRTiebreakersTable";
                  description "FRR tiebreakers configuration";

                  list frr-tiebreaker {
                    xr:xr-xml-map "isis_cfg:FRRTiebreaker";
                    key "level tiebreaker";
                    description
                      "Configure tiebreaker for multiple backups";
                    leaf level {
                      xr:xr-xml-map "isis_cfg:Level";
                      type dt1:Isis-internal-level;
                      description
                        "Level to which configuration applies";
                    }
                    leaf tiebreaker {
                      xr:xr-xml-map "isis_cfg:Tiebreaker";
                      type Isisfrr-tiebreaker;
                      description
                        "Tiebreaker for which configuration
                        applies";
                    }
                    leaf index {
                      xr:xr-xml-map "isis_cfg:Index";
                      type uint32 {
                        range "1..255";
                      }
                      mandatory true;
                      description
                        "Preference order among tiebreakers";
                    }
                  }
                }

                container frr-use-cand-onlies {
                  xr:xr-xml-map "isis_cfg:FRRUseCandOnlyTable";
                  description
                    "FRR use candidate only configuration";

                  list frr-use-cand-only {
                    xr:xr-xml-map "isis_cfg:FRRUseCandOnly";
                    key "level frr-type";
                    description
                      "Configure use candidate only to exclude
                      interfaces as backup";
                    leaf level {
                      xr:xr-xml-map "isis_cfg:Level";
                      type dt1:Isis-internal-level;
                      description
                        "Level to which configuration applies";
                    }
                    leaf frr-type {
                      xr:xr-xml-map "isis_cfg:FRRType";
                      type Isisfrr;
                      description "Computation Type";
                    }
                  }
                }
              }

              container router-id {
                xr:xr-xml-map "isis_cfg:RouterID";
                must "(address and not(interface-name)) or"+
                  " (not(address) and interface-name)" {
                  description
                    "Describes valid combinations of leafs";
                }
                description
                  "Stable IP address for system. Will only be
                  applied for the unicast sub-address-family.";
                leaf address {
                  xr:xr-xml-map "isis_cfg:Address";
                  type string;
                  description
                    "IPv4/IPv6 address to be used as a router
                    ID. Precisely one of Address and Interface
                    must be specified.";
                }
                leaf interface-name {
                  xr:xr-xml-map "isis_cfg:InterfaceName";
                  type xr:Interface-name;
                  description
                    "Interface with designated stable IP
                    address to be used as a router ID. This
                    must be a Loopback interface. Precisely
                    one of Address and Interface must be
                    specified.";
                }
              }

              container spf-prefix-priorities {
                xr:xr-xml-map "isis_cfg:SPFPrefixPriorityTable";
                description "SPF Prefix Priority configuration";

                list spf-prefix-priority {
                  xr:xr-xml-map "isis_cfg:SPFPrefixPriority";
                  must "(admin-tag and not(access-list-name)) or"+
                    " (not(admin-tag) and access-list-name)" {
                    description
                      "Describes valid combinations of leafs";
                  }
                  key "level prefix-priority-type";
                  description "Determine SPF priority for prefixes";
                  leaf level {
                    xr:xr-xml-map "isis_cfg:Level";
                    type dt1:Isis-internal-level;
                    description
                      "SPF Level for prefix prioritization";
                  }
                  leaf prefix-priority-type {
                    xr:xr-xml-map "isis_cfg:PrefixPriorityType";
                    type Isis-prefix-priority;
                    description
                      "SPF Priority to assign matching prefixes";
                  }
                  leaf admin-tag {
                    xr:xr-xml-map "isis_cfg:AdminTag";
                    type uint32 {
                      range "1..4294967295";
                    }
                    description
                      "Tag value to determine prefixes for this
                      priority";
                  }
                  leaf access-list-name {
                    xr:xr-xml-map "isis_cfg:AccessListName";
                    type string;
                    description
                      "Access List to determine prefixes for
                      this priority";
                  }
                }
              }

              container summary-prefixes {
                xr:xr-xml-map "isis_cfg:SummaryPrefixTable";
                description "Summary-prefix configuration";

                list summary-prefix {
                  xr:xr-xml-map "isis_cfg:SummaryPrefix";
                  key "address-prefix";
                  description
                    "Configure IP address prefixes to advertise";
                  leaf address-prefix {
                    xr:xr-xml-map "isis_cfg:AddressPrefix";
                    type inet:ip-prefix;
                    description "IP summary address prefix";
                  }
                  leaf tag {
                    xr:xr-xml-map "isis_cfg:Tag";
                    type uint32 {
                      range "1..4294967295";
                    }
                    description "The tag value";
                  }
                  leaf level {
                    xr:xr-xml-map "isis_cfg:Level";
                    type uint32 {
                      range "1..2";
                    }
                    description
                      "Level in which to summarize routes";
                  }
                }
              }

              container micro-loop-avoidance {
                xr:xr-xml-map "isis_cfg:MicroLoopAvoidance";
                description "Micro Loop Avoidance configuration";
                leaf enable {
                  xr:xr-xml-map "isis_cfg:Enable";
                  type Isis-micro-loop-avoidance;
                  default "micro-loop-avoidance-all";
                  description
                    "MicroLoop avoidance enable configuration";
                }
                leaf rib-update-delay {
                  xr:xr-xml-map "isis_cfg:RIBUpdateDelay";
                  type uint32 {
                    range "1000..65535";
                  }
                  units "millisecond";
                  default "5000";
                  description
                    "Value of delay in msecs in updating RIB";
                }
              }

              container ucmp {
                xr:xr-xml-map "isis_cfg:UCMP";
                description
                  "UCMP (UnEqual Cost MultiPath) configuration";

                container enable {
                  xr:xr-xml-map "isis_cfg:Enable";
                  description "UCMP feature enable configuration";
                  leaf variance {
                    xr:xr-xml-map "isis_cfg:Variance";
                    type uint32 {
                      range "101..10000";
                    }
                    default "200";
                    description "Value of variance";
                  }
                  leaf prefix-list-name {
                    xr:xr-xml-map "isis_cfg:PrefixListName";
                    type string;
                    description "Name of the Prefix List";
                  }
                }

                container exclude-interfaces {
                  xr:xr-xml-map "isis_cfg:ExcludeInterfaceTable";
                  description
                    "Interfaces excluded from UCMP path
                    computation";

                  list exclude-interface {
                    xr:xr-xml-map "isis_cfg:ExcludeInterface";
                    key "interface-name";
                    description
                      "Exclude this interface from UCMP path
                      computation";
                    leaf interface-name {
                      xr:xr-xml-map "isis_cfg:InterfaceName";
                      type xr:Interface-name;
                      description
                        "Name of the interface to be excluded";
                    }
                  }
                }
                leaf delay-interval {
                  xr:xr-xml-map "isis_cfg:DelayInterval";
                  type uint32 {
                    range "100..65535";
                  }
                  units "millisecond";
                  default "100";
                  description
                    "Delay in msecs between primary SPF and
                    UCMP computation";
                }
              }

              container max-redist-prefixes {
                xr:xr-xml-map "isis_cfg:MaxRedistPrefixTable";
                description
                  "Maximum number of redistributed
                  prefixesconfiguration";

                list max-redist-prefix {
                  xr:xr-xml-map "isis_cfg:MaxRedistPrefix";
                  key "level";
                  description
                    "An upper limit on the number of
                    redistributed prefixes which may be
                    included in the local system's LSP";
                  leaf level {
                    xr:xr-xml-map "isis_cfg:Level";
                    type dt1:Isis-internal-level;
                    description
                      "Level to which configuration applies";
                  }
                  leaf prefix-limit {
                    xr:xr-xml-map "isis_cfg:PrefixLimit";
                    type uint32 {
                      range "1..28000";
                    }
                    mandatory true;
                    description "Max number of prefixes";
                  }
                }
              }

              container propagations {
                xr:xr-xml-map "isis_cfg:PropagationTable";
                description "Route propagation configuration";

                list propagation {
                  xr:xr-xml-map "isis_cfg:Propagation";
                  key "source-level destination-level";
                  description
                    "Propagate routes between IS-IS levels";
                  leaf source-level {
                    xr:xr-xml-map "isis_cfg:SourceLevel";
                    type dt1:Isis-internal-level;
                    description "Source level for routes";
                  }
                  leaf destination-level {
                    xr:xr-xml-map "isis_cfg:DestinationLevel";
                    type dt1:Isis-internal-level;
                    description
                      "Destination level for routes.  Must
                      differ from SourceLevel";
                  }
                  leaf route-policy-name {
                    xr:xr-xml-map "isis_cfg:RoutePolicyName";
                    type string;
                    mandatory true;
                    description
                      "Route policy limiting routes to be
                      propagated";
                  }
                }
              }

              container redistributions {
                xr:xr-xml-map "isis_cfg:RedistributionTable";
                description "Protocol redistribution configuration";

                list redistribution {
                  xr:xr-xml-map "isis_cfg:Redistribution";
                  must "connected-or-static-or-rip-or-subscriber-or"+
                    "-mobile or"+
                    " ospf-or-ospfv3-or-isis-or-application or bgp"+
                    " or eigrp" {
                    description
                      "Connected-or-Static-or-RIP-or-Subscriber-or-Mobile or OSPF-or-OSPFv3-or-ISIS-or-Application or BGP or EIGRP must be present.";
                  }
                  key "protocol-name";
                  description
                    "Redistribution of other protocols into
                    this IS-IS instance";

                  grouping REDISTRIBUTION-CONTENT {
                    description "REDISTRIBUTION CONTENT";
                    leaf metric {
                      xr:xr-xml-map "isis_cfg:Metric";
                      type uint32 {
                        range "0..16777215";
                      }
                      description
                        "Metric for redistributed routes: <0-63>
                        for narrow, <0-16777215> for wide";
                    }
                    leaf levels {
                      xr:xr-xml-map "isis_cfg:Levels";
                      type Isis-configurable-levels;
                      description
                        "Levels to redistribute routes into";
                    }
                    leaf route-policy-name {
                      xr:xr-xml-map "isis_cfg:RoutePolicyName";
                      type string;
                      description
                        "Route policy to control redistribution.";
                    }
                    leaf metric-type {
                      xr:xr-xml-map "isis_cfg:MetricType";
                      type Isis-metric;
                      description "IS-IS metric type";
                    }
                    leaf ospf-route-type {
                      xr:xr-xml-map "isis_cfg:OSPFRouteType";
                      type int32;
                      description
                        "OSPF route types to redistribute.  May
                        only be specified if Protocol is OSPF.";
                    }
                  }

                  container "connected-or-static-or-rip-or"+
                    "-subscriber-or-mobile" {
                    when "../protocol-name = 'connected' or"+
                      " ../protocol-name = 'static' or"+
                      " ../protocol-name = 'rip' or"+
                      " ../protocol-name = 'subscriber' or"+
                      " ../protocol-name = 'mobile'" {
                        description
                          "../ProtocolName = Connected or .
                          ./ProtocolName = Static or .
                          ./ProtocolName = RIP or ../ProtocolName
                          = Subscriber or ../ProtocolName =
                          Mobile";
                    }
                    presence "Indicates that this node is"+
                      " configured.";
                    description
                      "connected or static or rip or subscriber
                      or mobile";
                    uses REDISTRIBUTION-CONTENT;
                  }
                  leaf protocol-name {
                    xr:xr-xml-map "isis_cfg:ProtocolName";
                    type Isis-redist-proto;
                    description
                      "The protocol to be redistributed.  OSPFv3
                      may not be specified for an IPv4 topology
                      and OSPF may not be specified for an IPv6
                      topology.";
                  }

                  list ospf-or-ospfv3-or-isis-or-application {
                    when "../protocol-name = 'ospf' or"+
                      " ../protocol-name = 'ospfv3' or"+
                      " ../protocol-name = 'isis' or"+
                      " ../protocol-name = 'application'" {
                        description
                          "../ProtocolName = OSPF or .
                          ./ProtocolName = OSPFv3 or .
                          ./ProtocolName = ISIS or .
                          ./ProtocolName = Application";
                    }
                    key "instance-name";
                    description
                      "ospf or ospfv3 or isis or application";
                    leaf instance-name {
                      xr:xr-xml-map "isis_cfg:InstanceName";
                      type xr:Cisco-ios-xr-string;
                      description
                        "Protocol Instance Identifier.  Mandatory
                        for ISIS, OSPF and application, must not
                        be specified otherwise.";
                    }
                    uses REDISTRIBUTION-CONTENT;
                  }

                  list bgp {
                    when "../protocol-name = 'bgp'" {
                      description "../ProtocolName = BGP";
                    }
                    key "as-xx as-yy";
                    description "bgp";
                    leaf as-xx {
                      xr:xr-xml-map "isis_cfg:AS_XX";
                      type uint32 {
                        range "0..65535";
                      }
                      description
                        "First half of BGP AS number in XX.YY
                        format.  Mandatory if Protocol is BGP
                        and must not be specified otherwise.
                        Must be a non-zero value if second half
                        is zero.";
                    }
                    leaf as-yy {
                      xr:xr-xml-map "isis_cfg:AS_YY";
                      type uint32 {
                        range "0..4294967295";
                      }
                      description
                        "Second half of BGP AS number in XX.YY
                        format. Mandatory if Protocol is BGP and
                        must not be specified otherwise. Must be
                        a non-zero value if first half is zero.";
                    }
                    uses REDISTRIBUTION-CONTENT;
                  }

                  list eigrp {
                    when "../protocol-name = 'eigrp'" {
                      description "../ProtocolName = EIGRP";
                    }
                    key "as-zz";
                    description "eigrp";
                    leaf as-zz {
                      xr:xr-xml-map "isis_cfg:AS_ZZ";
                      type uint32 {
                        range "1..65535";
                      }
                      description "Eigrp as number.";
                    }
                    uses REDISTRIBUTION-CONTENT;
                  }
                }
              }

              container spf-periodic-intervals {
                xr:xr-xml-map "isis_cfg:SPFPeriodicTable";
                description "Peoridic SPF configuration";

                list spf-periodic-interval {
                  xr:xr-xml-map "isis_cfg:SPFPeriodicInterval";
                  key "level";
                  description "Maximum interval between spf runs";
                  leaf level {
                    xr:xr-xml-map "isis_cfg:Level";
                    type dt1:Isis-internal-level;
                    description
                      "Level to which configuration applies";
                  }
                  leaf periodic-interval {
                    xr:xr-xml-map "isis_cfg:PeriodicInterval";
                    type uint32 {
                      range "0..3600";
                    }
                    units "second";
                    mandatory true;
                    description
                      "Maximum interval in between SPF runs in
                      seconds";
                  }
                }
              }

              container spf-intervals {
                xr:xr-xml-map "isis_cfg:SPFIntervalTable";
                description "SPF-interval configuration";

                list spf-interval {
                  xr:xr-xml-map "isis_cfg:SPFInterval";
                  key "level";
                  description
                    "Route calculation scheduling parameters";
                  leaf level {
                    xr:xr-xml-map "isis_cfg:Level";
                    type dt1:Isis-internal-level;
                    description
                      "Level to which configuration applies";
                  }
                  leaf maximum-wait {
                    xr:xr-xml-map "isis_cfg:MaximumWait";
                    type uint32 {
                      range "0..120000";
                    }
                    units "millisecond";
                    description
                      "Maximum wait before running a route
                      calculation in milliseconds";
                  }
                  leaf initial-wait {
                    xr:xr-xml-map "isis_cfg:InitialWait";
                    type uint32 {
                      range "0..120000";
                    }
                    units "millisecond";
                    description
                      "Initial wait before running a route
                      calculation in milliseconds";
                  }
                  leaf secondary-wait {
                    xr:xr-xml-map "isis_cfg:SecondaryWait";
                    type uint32 {
                      range "0..120000";
                    }
                    units "millisecond";
                    description
                      "Secondary wait before running a route
                      calculation in milliseconds";
                  }
                }
              }

              container monitor-convergence {
                xr:xr-xml-map "isis_cfg:MonitorConvergence";
                description "Enable convergence monitoring";
                leaf enable {
                  xr:xr-xml-map "isis_cfg:Enable";
                  type empty;
                  description "Enable convergence monitoring";
                }
                leaf track-ip-frr {
                  xr:xr-xml-map "isis_cfg:TrackIpFrr";
                  type empty;
                  description
                    "Enable the Tracking of IP-Frr Convergence";
                }
                leaf prefix-list {
                  xr:xr-xml-map "isis_cfg:PrefixList";
                  type string;
                  description
                    "Enable the monitoring of individual
                    prefixes (prefix list name)";
                }
              }

              container default-information {
                xr:xr-xml-map "isis_cfg:DefaultInformation";
                description
                  "Control origination of a default route with
                  the option of using a policy.  If no policy
                  is specified the default route is
                  advertised with zero cost in level 2 only.";
                leaf use-policy {
                  xr:xr-xml-map "isis_cfg:UsePolicy";
                  type boolean;
                  description
                    "Flag to indicate whether default
                    origination is controlled using a policy";
                }
                leaf policy-name {
                  xr:xr-xml-map "isis_cfg:PolicyName";
                  when "../use-policy != 'false'" {
                    description "../UsePolicy != 0";
                  }
                  type string;
                  description "Policy name";
                }
                leaf external {
                  xr:xr-xml-map "isis_cfg:External";
                  type empty;
                  description
                    "Flag to indicate that the default prefix
                    should be originated as an external route";
                }
              }

              container admin-distances {
                xr:xr-xml-map "isis_cfg:AdminDistanceTable";
                description
                  "Per-route administrative
                  distanceconfiguration";

                list admin-distance {
                  xr:xr-xml-map "isis_cfg:AdminDistance";
                  key "address-prefix";
                  description
                    "Administrative distance configuration. The
                    supplied distance is applied to all routes
                    discovered from the specified source, or
                    only those that match the supplied prefix
                    list if this is specified";
                  leaf address-prefix {
                    xr:xr-xml-map "isis_cfg:AddressPrefix";
                    type inet:ip-prefix;
                    description "IP route source prefix";
                  }
                  leaf distance {
                    xr:xr-xml-map "isis_cfg:Distance";
                    type uint32 {
                      range "1..255";
                    }
                    mandatory true;
                    description "Administrative distance";
                  }
                  leaf prefix-list {
                    xr:xr-xml-map "isis_cfg:PrefixList";
                    type string;
                    description
                      "List of prefixes to which this distance
                      applies";
                  }
                }
              }

              container ispf {
                xr:xr-xml-map "isis_cfg:ISPF";
                description "ISPF configuration";

                container states {
                  xr:xr-xml-map "isis_cfg:StateTable";
                  description "ISPF state (enable/disable)";

                  list state {
                    xr:xr-xml-map "isis_cfg:State";
                    key "level";
                    description "Enable/disable ISPF";
                    leaf level {
                      xr:xr-xml-map "isis_cfg:Level";
                      type dt1:Isis-internal-level;
                      description
                        "Level to which configuration applies";
                    }
                    leaf state {
                      xr:xr-xml-map "isis_cfg:State";
                      type Isisispf-state;
                      mandatory true;
                      description "State";
                    }
                  }
                }
              }

              container mpls-ldp-global {
                xr:xr-xml-map "isis_cfg:MPLS_LDPGlobal";
                description
                  "MPLS LDP configuration. MPLS LDP
                  configuration will only be applied for the
                  IPv4-unicast address-family.";
                leaf auto-config {
                  xr:xr-xml-map "isis_cfg:AutoConfig";
                  type boolean;
                  description
                    "If TRUE, LDP will be enabled onall IS-IS
                    interfaces enabled for this address-family";
                }
              }

              container mpls {
                xr:xr-xml-map "isis_cfg:MPLS";
                description
                  "MPLS configuration. MPLS configuration will
                  only be applied for the IPv4-unicast
                  address-family.";

                container router-id {
                  xr:xr-xml-map "isis_cfg:RouterID";
                  must "(address and not(interface-name)) or"+
                    " (not(address) and interface-name)" {
                    description
                      "Describes valid combinations of leafs";
                  }
                  description
                    "Traffic Engineering stable IP address for
                    system";
                  leaf address {
                    xr:xr-xml-map "isis_cfg:Address";
                    type inet:ipv4-address-no-zone;
                    description
                      "IPv4 address to be used as a router ID.
                      Precisely one of Address and Interface
                      must be specified.";
                  }
                  leaf interface-name {
                    xr:xr-xml-map "isis_cfg:InterfaceName";
                    type xr:Interface-name;
                    description
                      "Interface with designated stable IP
                      address to be used as a router ID. This
                      must be a Loopback interface. Precisely
                      one of Address and Interface must be
                      specified.";
                  }
                }
                leaf igp-intact {
                  xr:xr-xml-map "isis_cfg:IGPIntact";
                  type empty;
                  description
                    "Install TE and non-TE nexthops in the RIB";
                }
                leaf level {
                  xr:xr-xml-map "isis_cfg:Level";
                  type Isis-configurable-levels;
                  description
                    "Enable MPLS for an IS-IS at the given
                    levels";
                }
                leaf multicast-intact {
                  xr:xr-xml-map "isis_cfg:MulticastIntact";
                  type empty;
                  description
                    "Install non-TE nexthops in the RIB for use
                    by multicast";
                }
              }
              leaf maximum-paths {
                xr:xr-xml-map "isis_cfg:MaximumPaths";
                type uint32 {
                  range "1..64";
                }
                description
                  "Maximum number of active parallel paths per
                  route";
              }
              leaf topology-id {
                xr:xr-xml-map "isis_cfg:TopologyID";
                type uint32 {
                  range "6..4095";
                }
                description
                  "Set the topology ID for a named
                  (non-default) topology. This object must be
                  set before any other configuration is
                  supplied for a named (non-default) topology
                  , and must be the last configuration object
                  to be removed. This item should not be
                  supplied for the non-named default
                  topologies.";
              }
              leaf single-topology {
                xr:xr-xml-map "isis_cfg:SingleTopology";
                type empty;
                description
                  "Run IPv6 Unicast using the standard (IPv4
                  Unicast) topology";
              }
              leaf adjacency-check {
                xr:xr-xml-map "isis_cfg:AdjacencyCheck";
                type Isis-adj-check;
                description
                  "Suppress check for consistent AF support on
                  received IIHs";
              }
              leaf advertise-link-attributes {
                xr:xr-xml-map "isis_cfg:AdvertiseLinkAttributes";
                type boolean;
                description
                  "If TRUE, advertise additional link
                  attributes in our LSP";
              }
              leaf apply-weight {
                xr:xr-xml-map "isis_cfg:ApplyWeight";
                type Isis-apply-weight;
                description "Apply weights to UCMP or ECMP only";
              }
              leaf default-admin-distance {
                xr:xr-xml-map "isis_cfg:DefaultAdminDistance";
                type uint32 {
                  range "1..255";
                }
                default "115";
                description
                  "Default IS-IS administrative distance
                  configuration.";
              }
              leaf advertise-passive-only {
                xr:xr-xml-map "isis_cfg:AdvertisePassiveOnly";
                type empty;
                description
                  "If enabled, advertise prefixes of passive
                  interfaces only";
              }
              leaf ignore-attached-bit {
                xr:xr-xml-map "isis_cfg:IgnoreAttachedBit";
                type boolean;
                description
                  "If TRUE, Ignore other routers attached bit";
              }
              leaf attached-bit {
                xr:xr-xml-map "isis_cfg:AttachedBit";
                type Isis-attached-bit;
                default "area";
                description
                  "Set the attached bit in this router's level
                  1 System LSP";
              }
              leaf route-source-first-hop {
                xr:xr-xml-map "isis_cfg:RouteSourceFirstHop";
                type boolean;
                description
                  "If TRUE, routes will be installed with the
                  IP address of the first-hop node as the
                  source instead of the originating node";
              }
              uses METRIC-TABLE;
              uses WEIGHT-TABLE;
            }

            container af-data {
              xr:xr-xml-map "isis_cfg:AF";
              presence "Indicates a af-data node is configured.";
              description "Data container.";
              uses AF-CONTENT;
            }
            leaf af-name {
              xr:xr-xml-map "isis_cfg:AFName";
              type dt1:Isis-address-family;
              description "Address family";
            }
            leaf saf-name {
              xr:xr-xml-map "isis_cfg:SAFName";
              type dt1:Isis-sub-address-family;
              description "Sub address family";
            }

            list topology-name {
              xr:xr-xml-map "isis_cfg:AF";
              key "topology-name";
              description "keys: topology-name";
              leaf topology-name {
                xr:xr-xml-map "isis_cfg:TopologyName";
                type dt1:Isis-topology-name;
                description "Topology Name";
              }
              uses AF-CONTENT;
            }
          }
        }

        container lsp-refresh-intervals {
          xr:xr-xml-map "isis_cfg:LSPRefreshIntervalTable";
          description "LSP refresh-interval configuration";

          list lsp-refresh-interval {
            xr:xr-xml-map "isis_cfg:LSPRefreshInterval";
            xr:xr-cli-map "isis <string> lsp-refresh-interval <numb"+
              "er> [level <number>] ";
            key "level";
            description
              "Interval between re-flooding of unchanged
              LSPs";
            leaf level {
              xr:xr-xml-map "isis_cfg:Level";
              type dt1:Isis-internal-level;
              description "Level to which configuration applies";
            }
            leaf interval {
              xr:xr-xml-map "isis_cfg:Interval";
              type uint32 {
                range "1..65535";
              }
              units "second";
              mandatory true;
              description "Seconds";
            }
          }
        }

        container distribute {
          xr:xr-xml-map "isis_cfg:Distribute";
          presence "enable distribute";
          description "IS-IS Distribute BGP-LS configuration";
          leaf dist-inst-id {
            xr:xr-xml-map "isis_cfg:DistInstId";
            type uint32 {
              range "1..65535";
            }
            description "Instance ID";
          }
          leaf level {
            xr:xr-xml-map "isis_cfg:Level";
            type Isis-configurable-levels;
            description "Level";
          }
          leaf dist-throttle {
            xr:xr-xml-map "isis_cfg:DistThrottle";
            type uint32 {
              range "5..20";
            }
            units "second";
            description "Seconds";
          }
        }

        container lsp-accept-passwords {
          xr:xr-xml-map "isis_cfg:LSPAcceptPasswordTable";
          description "LSP/SNP accept password configuration";

          list lsp-accept-password {
            xr:xr-xml-map "isis_cfg:LSPAcceptPassword";
            xr:xr-cli-map "isis <string> lsp-password accept ([0] <"+
              "string>)|(clear)|((7)|(encrypted) <string>)|(<string"+
              ">) [level <number>] ";
            key "level";
            description
              "LSP/SNP accept passwords. This requires the
              existence of an LSPPassword of the same level
              .";
            leaf level {
              xr:xr-xml-map "isis_cfg:Level";
              type dt1:Isis-internal-level;
              description "Level to which configuration applies";
            }
            leaf password {
              xr:xr-xml-map "isis_cfg:Password";
              type xr:Proprietary-password;
              mandatory true;
              description "Password";
            }
          }
        }

        container lsp-mtus {
          xr:xr-xml-map "isis_cfg:LSP_MTUTable";
          description "LSP MTU configuration";

          list lsp-mtu {
            xr:xr-xml-map "isis_cfg:LSP_MTU";
            xr:xr-cli-map "isis <string> lsp-mtu <number> [level <n"+
              "umber>] ";
            key "level";
            description "LSP MTU";
            leaf level {
              xr:xr-xml-map "isis_cfg:Level";
              type dt1:Isis-internal-level;
              description "Level to which configuration applies";
            }
            leaf mtu {
              xr:xr-xml-map "isis_cfg:MTU";
              type uint32 {
                range "128..4352";
              }
              units "byte";
              mandatory true;
              description "Bytes";
            }
          }
        }

        container nsf {
          xr:xr-xml-map "isis_cfg:NSF";
          description "IS-IS NSF configuration";
          leaf flavor {
            xr:xr-xml-map "isis_cfg:Flavor";
            xr:xr-cli-map "isis <string> nsf [enable] (cisco)|(ietf"+
              ")] ";
            type Isis-nsf-flavor;
            description "NSF not configured if item is deleted";
          }
          leaf interface-timer {
            xr:xr-xml-map "isis_cfg:InterfaceTimer";
            xr:xr-cli-map "isis <string> nsf interface-timer <numbe"+
              "r> ";
            type uint32 {
              range "1..20";
            }
            units "second";
            default "1";
            description
              "Per-interface time period to wait for a
              restart ACK during an IETF-NSF restart. This
              configuration has no effect if IETF-NSF is
              not configured";
          }
          leaf max-interface-timer-expiry {
            xr:xr-xml-map "isis_cfg:MaxInterfaceTimerExpiry";
            xr:xr-cli-map "isis <string> nsf interface-expires <num"+
              "ber> ";
            type uint32 {
              range "1..10";
            }
            default "10";
            description
              "Maximum number of times an interface timer
              may expire during an IETF-NSF restart before
              the NSF restart is aborted. This
              configuration has no effect if IETF NSF is
              not configured.";
          }
          leaf lifetime {
            xr:xr-xml-map "isis_cfg:Lifetime";
            xr:xr-cli-map "isis <string> nsf lifetime <number> ";
            type uint32 {
              range "5..300";
            }
            units "second";
            default "90";
            description
              "Maximum route lifetime following restart.
              When this lifetime expires, old routes will
              be purged from the RIB.";
          }
        }

        container link-groups {
          xr:xr-xml-map "isis_cfg:LinkGroupTable";
          description "Link Group";

          list link-group {
            xr:xr-xml-map "isis_cfg:LinkGroup";
            key "link-group-name";
            description "Configuration for link group name";
            leaf enable {
              xr:xr-xml-map "isis_cfg:Enable";
              type empty;
              description
                "Flag to indicate that linkgroup should be
                running.  This must be the first object
                created when a linkgroup is configured, and
                the last object deleted when it is
                deconfigured.  When this object is deleted,
                the IS-IS linkgroup will be removed.";
            }
            leaf metric-offset {
              xr:xr-xml-map "isis_cfg:MetricOffset";
              xr:xr-cli-map "isis <string> link-group <string> metr"+
                "ic-offset (maximum)|(<number>)|(16777215) ";
              type uint32 {
                range "0..16777215";
              }
              description
                "Metric for redistributed routes: <0-63> for
                narrow, <0-16777215> for wide";
            }
            leaf revert-members {
              xr:xr-xml-map "isis_cfg:RevertMembers";
              xr:xr-cli-map "isis <string> link-group <string> reve"+
                "rt-members <number> ";
              type uint32 {
                range "2..64";
              }
              default "2";
              description "Revert Members";
            }
            leaf minimum-members {
              xr:xr-xml-map "isis_cfg:MinimumMembers";
              xr:xr-cli-map "isis <string> link-group <string> mini"+
                "mum-members <number> ";
              type uint32 {
                range "2..64";
              }
              default "2";
              description "Minimum Members";
            }
            leaf link-group-name {
              xr:xr-xml-map "isis_cfg:LinkGroupName";
              type dt1:Isis-link-group-name;
              description "Link Group Name";
            }
          }
        }

        container lsp-check-intervals {
          xr:xr-xml-map "isis_cfg:LSPCheckIntervalTable";
          description "LSP checksum check interval configuration";

          list lsp-check-interval {
            xr:xr-xml-map "isis_cfg:LSPCheckInterval";
            xr:xr-cli-map "isis <string> lsp-check-interval <number"+
              "> [level <number>] ";
            key "level";
            description "LSP checksum check interval parameters";
            leaf level {
              xr:xr-xml-map "isis_cfg:Level";
              type dt1:Isis-internal-level;
              description "Level to which configuration applies";
            }
            leaf interval {
              xr:xr-xml-map "isis_cfg:Interval";
              type uint32 {
                range "10..65535";
              }
              units "second";
              mandatory true;
              description
                "LSP checksum check interval time in seconds";
            }
          }
        }

        container lsp-passwords {
          xr:xr-xml-map "isis_cfg:LSPPasswordTable";
          description "LSP/SNP password configuration";

          list lsp-password {
            xr:xr-xml-map "isis_cfg:LSPPassword";
            xr:xr-cli-map "isis <string> lsp-password [[text] ([0] "+
              "<string>)|(clear)|((7)|(encrypted) <string>)|(<strin"+
              "g>)]|hmac-md5|keychain <string>] [level <number>|sen"+
              "d-only|snp (send-only)|(validate)] ";
            key "level";
            description
              "LSP/SNP passwords. This must exist if an
              LSPAcceptPassword of the same level exists.";
            leaf level {
              xr:xr-xml-map "isis_cfg:Level";
              type dt1:Isis-internal-level;
              description "Level to which configuration applies";
            }
            leaf algorithm {
              xr:xr-xml-map "isis_cfg:Algorithm";
              type Isis-authentication-algorithm;
              mandatory true;
              description "Algorithm";
            }
            leaf failure-mode {
              xr:xr-xml-map "isis_cfg:FailureMode";
              type Isis-authentication-failure-mode;
              mandatory true;
              description "Failure Mode";
            }
            leaf authentication-type {
              xr:xr-xml-map "isis_cfg:AuthenticationType";
              type Isis-snp-auth;
              mandatory true;
              description "SNP packet authentication mode";
            }
            leaf password {
              xr:xr-xml-map "isis_cfg:Password";
              type xr:Proprietary-password;
              mandatory true;
              description "Password or unencrypted Key Chain name";
            }
          }
        }

        container nets {
          xr:xr-xml-map "isis_cfg:NETTable";
          description "NET configuration";

          list net {
            xr:xr-xml-map "isis_cfg:NET";
            xr:xr-cli-map "isis <string> net <string> ";
            key "net-name";
            description "Network Entity Title (NET)";
            leaf net-name {
              xr:xr-xml-map "isis_cfg:NETName";
              type xr:Osi-net;
              description "Network Entity Title";
            }
          }
        }

        container lsp-lifetimes {
          xr:xr-xml-map "isis_cfg:LSPLifetimeTable";
          description "LSP lifetime configuration";

          list lsp-lifetime {
            xr:xr-xml-map "isis_cfg:LSPLifetime";
            xr:xr-cli-map "isis <string> max-lsp-lifetime <number> "+
              "[level <number>] ";
            key "level";
            description "Maximum LSP lifetime";
            leaf level {
              xr:xr-xml-map "isis_cfg:Level";
              type dt1:Isis-internal-level;
              description "Level to which configuration applies";
            }
            leaf lifetime {
              xr:xr-xml-map "isis_cfg:Lifetime";
              type uint32 {
                range "1..65535";
              }
              units "second";
              mandatory true;
              description "Seconds";
            }
          }
        }

        container overload-bits {
          xr:xr-xml-map "isis_cfg:OverloadBitTable";
          description "LSP overload-bit configuration";

          list overload-bit {
            xr:xr-xml-map "isis_cfg:OverloadBit";
            xr:xr-cli-map "isis <string> set-overload-bit [on-start"+
              "up (<number>)|(wait-for-bgp)] [level <number>] [adve"+
              "rtise (external)|(interlevel)] ";
            key "level";
            description
              "Set the overload bit in the System LSP so
              that other routers avoid this one in SPF
              calculations. This may be done either
              unconditionally, or on startup until either a
              set time has passed or IS-IS is informed that
              BGP has converged. This is an Object with a
              union discriminated on an integer value of
              the ISISOverloadBitModeType.";
            leaf level {
              xr:xr-xml-map "isis_cfg:Level";
              type dt1:Isis-internal-level;
              description "Level to which configuration applies";
            }
            leaf overload-bit-mode {
              xr:xr-xml-map "isis_cfg:OverloadBitMode";
              type Isis-overload-bit-mode;
              description
                "Circumstances under which the overload bit
                is set in the system LSP";
            }
            leaf hippity-period {
              xr:xr-xml-map "isis_cfg:HippityPeriod";
              when "../overload-bit-mode = 'startup-period'" {
                description "../OverloadBitMode = 2";
              }
              type uint32 {
                range "5..86400";
              }
              units "second";
              description
                "Time in seconds to advertise ourself as
                overloaded after process startup";
            }
            leaf external-adv-type {
              xr:xr-xml-map "isis_cfg:ExternalAdvType";
              type Isis-adv-type-external;
              description "Advertise prefixes from other protocols";
            }
            leaf inter-level-adv-type {
              xr:xr-xml-map "isis_cfg:InterLevelAdvType";
              type Isis-adv-type-inter-level;
              description "Advertise prefixes across ISIS levels";
            }
          }
        }

        container interfaces {
          xr:xr-xml-map "isis_cfg:InterfaceTable";
          description "Per-interface configuration";

          list interface {
            xr:xr-xml-map "isis_cfg:Interface";
            key "interface-name";
            description "Configuration for an IS-IS interface";

            container lsp-retransmit-throttle-intervals {
              xr:xr-xml-map "isis_cfg:LSPRetransmitThrottleInterval"+
                "Table";
              description
                "LSP-retransmission-throttle-interval
                configuration";

              list lsp-retransmit-throttle-interval {
                xr:xr-xml-map "isis_cfg:LSPRetransmitThrottleInterv"+
                  "al";
                xr:xr-cli-map "isis <string> interface <interface> "+
                  "retransmit-throttle-interval <number> [level <nu"+
                  "mber>] ";
                key "level";
                description
                  "Minimum interval betwen retransissions of
                  different LSPs";
                leaf level {
                  xr:xr-xml-map "isis_cfg:Level";
                  type dt1:Isis-internal-level;
                  description
                    "Level to which configuration applies";
                }
                leaf interval {
                  xr:xr-xml-map "isis_cfg:Interval";
                  type uint32 {
                    range "0..65535";
                  }
                  units "millisecond";
                  mandatory true;
                  description "Milliseconds";
                }
              }
            }

            container lsp-retransmit-intervals {
              xr:xr-xml-map "isis_cfg:LSPRetransmitIntervalTable";
              description
                "LSP-retransmission-interval configuration";

              list lsp-retransmit-interval {
                xr:xr-xml-map "isis_cfg:LSPRetransmitInterval";
                xr:xr-cli-map "isis <string> interface <interface> "+
                  "retransmit-interval <number> [level <number>] ";
                key "level";
                description
                  "Interval between retransmissions of the
                  same LSP";
                leaf level {
                  xr:xr-xml-map "isis_cfg:Level";
                  type dt1:Isis-internal-level;
                  description
                    "Level to which configuration applies";
                }
                leaf interval {
                  xr:xr-xml-map "isis_cfg:Interval";
                  type uint32 {
                    range "0..65535";
                  }
                  units "second";
                  mandatory true;
                  description "Seconds";
                }
              }
            }

            container bfd {
              xr:xr-xml-map "isis_cfg:BFD";
              description "BFD configuration";
              leaf enable-ipv6 {
                xr:xr-xml-map "isis_cfg:EnableIPV6";
                xr:xr-cli-map "isis <string> interface <interface> "+
                  "bfd fast-detect ipv6 ";
                type boolean;
                description
                  "TRUE to enable BFD. FALSE to disable and to
                  prevent inheritance from a parent";
              }
              leaf enable-ipv4 {
                xr:xr-xml-map "isis_cfg:EnableIPV4";
                xr:xr-cli-map "isis <string> interface <interface> "+
                  "bfd fast-detect ipv4 ";
                type boolean;
                description
                  "TRUE to enable BFD. FALSE to disable and to
                  prevent inheritance from a parent";
              }
              leaf interval {
                xr:xr-xml-map "isis_cfg:Interval";
                xr:xr-cli-map "isis <string> interface <interface> "+
                  "bfd minimum-interval <number> ";
                type uint32 {
                  range "3..30000";
                }
                units "millisecond";
                description
                  "Hello interval for BFD sessions created by
                  isis";
              }
              leaf detection-multiplier {
                xr:xr-xml-map "isis_cfg:DetectionMultiplier";
                xr:xr-cli-map "isis <string> interface <interface> "+
                  "bfd multiplier <number> ";
                type uint32 {
                  range "2..50";
                }
                description
                  "Detection multiplier for BFD sessions
                  created by isis";
              }
            }

            container priorities {
              xr:xr-xml-map "isis_cfg:PriorityTable";
              description "DIS-election priority configuration";

              list priority {
                xr:xr-xml-map "isis_cfg:Priority";
                xr:xr-cli-map "isis <string> interface <interface> "+
                  "priority <number> [level <number>] ";
                key "level";
                description "DIS-election priority";
                leaf level {
                  xr:xr-xml-map "isis_cfg:Level";
                  type dt1:Isis-internal-level;
                  description
                    "Level to which configuration applies";
                }
                leaf priority-value {
                  xr:xr-xml-map "isis_cfg:PriorityValue";
                  type uint32 {
                    range "0..127";
                  }
                  mandatory true;
                  description "Priority";
                }
              }
            }

            container hello-accept-passwords {
              xr:xr-xml-map "isis_cfg:HelloAcceptPasswordTable";
              description "IIH accept password configuration";

              list hello-accept-password {
                xr:xr-xml-map "isis_cfg:HelloAcceptPassword";
                xr:xr-cli-map "isis <string> interface <interface> "+
                  "hello-password accept ([0] <string>)|(clear)|((7"+
                  ")|(encrypted) <string>)|(<string>) [level <numbe"+
                  "r>] ";
                key "level";
                description
                  "IIH accept passwords. This requires the
                  existence of a HelloPassword of the same
                  level.";
                leaf level {
                  xr:xr-xml-map "isis_cfg:Level";
                  type dt1:Isis-internal-level;
                  description
                    "Level to which configuration applies";
                }
                leaf password {
                  xr:xr-xml-map "isis_cfg:Password";
                  type xr:Proprietary-password;
                  mandatory true;
                  description "Password";
                }
              }
            }

            container hello-passwords {
              xr:xr-xml-map "isis_cfg:HelloPasswordTable";
              description "IIH password configuration";

              list hello-password {
                xr:xr-xml-map "isis_cfg:HelloPassword";
                xr:xr-cli-map "isis <string> interface <interface> "+
                  "hello-password [[text] ([0] <string>)|(clear)|(("+
                  "7)|(encrypted) <string>)|(<string>)]|hmac-md5|ke"+
                  "ychain <string>] [level <number>|send-only] ";
                key "level";
                description
                  "IIH passwords. This must exist if a
                  HelloAcceptPassword of the same level
                  exists.";
                leaf level {
                  xr:xr-xml-map "isis_cfg:Level";
                  type dt1:Isis-internal-level;
                  description
                    "Level to which configuration applies";
                }
                leaf algorithm {
                  xr:xr-xml-map "isis_cfg:Algorithm";
                  type Isis-authentication-algorithm;
                  mandatory true;
                  description "Algorithm";
                }
                leaf failure-mode {
                  xr:xr-xml-map "isis_cfg:FailureMode";
                  type Isis-authentication-failure-mode;
                  mandatory true;
                  description "Failure Mode";
                }
                leaf password {
                  xr:xr-xml-map "isis_cfg:Password";
                  type xr:Proprietary-password;
                  mandatory true;
                  description
                    "Password or unencrypted Key Chain name";
                }
              }
            }

            container hello-paddings {
              xr:xr-xml-map "isis_cfg:HelloPaddingTable";
              description "Hello-padding configuration";

              list hello-padding {
                xr:xr-xml-map "isis_cfg:HelloPadding";
                xr:xr-cli-map "isis <string> interface <interface> "+
                  "hello-padding (disable)|(sometimes) [level <numb"+
                  "er>] ";
                key "level";
                description "Pad IIHs to the interface MTU";
                leaf level {
                  xr:xr-xml-map "isis_cfg:Level";
                  type dt1:Isis-internal-level;
                  description
                    "Level to which configuration applies";
                }
                leaf padding-type {
                  xr:xr-xml-map "isis_cfg:PaddingType";
                  type Isis-hello-padding;
                  mandatory true;
                  description "Hello padding type value";
                }
              }
            }

            container hello-multipliers {
              xr:xr-xml-map "isis_cfg:HelloMultiplierTable";
              description "Hello-multiplier configuration";

              list hello-multiplier {
                xr:xr-xml-map "isis_cfg:HelloMultiplier";
                xr:xr-cli-map "isis <string> interface <interface> "+
                  "hello-multiplier <number> [level <number>] ";
                key "level";
                description
                  "Hello-multiplier configuration. The number
                  of successive IIHs that may be missed on an
                  adjacency before it is considered down.";
                leaf level {
                  xr:xr-xml-map "isis_cfg:Level";
                  type dt1:Isis-internal-level;
                  description
                    "Level to which configuration applies";
                }
                leaf multiplier {
                  xr:xr-xml-map "isis_cfg:Multiplier";
                  type uint32 {
                    range "3..1000";
                  }
                  mandatory true;
                  description "Hello multiplier value";
                }
              }
            }

            container lsp-fast-flood-thresholds {
              xr:xr-xml-map "isis_cfg:LSPFastFloodThresholdTable";
              description "LSP fast flood threshold configuration";

              list lsp-fast-flood-threshold {
                xr:xr-xml-map "isis_cfg:LSPFastFloodThreshold";
                xr:xr-cli-map "isis <string> interface <interface> "+
                  "lsp fast-flood threshold <number> [level <number"+
                  ">] ";
                key "level";
                description
                  "Number of LSPs to send back to back on an
                  interface.";
                leaf level {
                  xr:xr-xml-map "isis_cfg:Level";
                  type dt1:Isis-internal-level;
                  description
                    "Level to which configuration applies";
                }
                leaf count {
                  xr:xr-xml-map "isis_cfg:Count";
                  type uint32 {
                    range "1..4294967295";
                  }
                  mandatory true;
                  description "Count";
                }
              }
            }

            container hello-intervals {
              xr:xr-xml-map "isis_cfg:HelloIntervalTable";
              description "Hello-interval configuration";

              list hello-interval {
                xr:xr-xml-map "isis_cfg:HelloInterval";
                xr:xr-cli-map "isis <string> interface <interface> "+
                  "hello-interval <number> [level <number>] ";
                key "level";
                description
                  "Hello-interval configuration. The interval
                  at which IIH packets will be sent. This
                  will be three times quicker on a LAN
                  interface which has been electted DIS.";
                leaf level {
                  xr:xr-xml-map "isis_cfg:Level";
                  type dt1:Isis-internal-level;
                  description
                    "Level to which configuration applies";
                }
                leaf interval {
                  xr:xr-xml-map "isis_cfg:Interval";
                  type uint32 {
                    range "1..65535";
                  }
                  units "second";
                  mandatory true;
                  description "Seconds";
                }
              }
            }

            container interface-afs {
              xr:xr-xml-map "isis_cfg:InterfaceAFTable";
              description
                "Per-interface address-family configuration";

              list interface-af {
                must "interface-af-data or topology-name" {
                  description
                    "interface-af-data or topology-name must be
                    present.";
                }
                key "saf-name af-name";
                description
                  "Configuration for an IS-IS address-family
                  on a single interface. If a named
                  (non-default) topology is being created it
                  must be multicast. Also the topology ID
                  mustbe set first and delete last in the
                  router configuration.";

                grouping INTERFACE-AF-CONTENT {
                  description "Content grouping.";

                  container prefix-sid {
                    xr:xr-xml-map "isis_cfg:PrefixSID";
                    presence "Indicates a prefix-sid node is"+
                      " configured.";
                    description
                      "Assign prefix SID to an interface,
                      ISISPHPFlag will be rejected if set to
                      disable, ISISEXPLICITNULLFlag will
                      override the value of ISISPHPFlag";
                    leaf type {
                      xr:xr-xml-map "isis_cfg:Type";
                      type Isissid;
                      mandatory true;
                      description "SID type for the interface";
                    }
                    leaf value {
                      xr:xr-xml-map "isis_cfg:Value";
                      type uint32 {
                        range "0..1048575";
                      }
                      mandatory true;
                      description "SID value for the interface";
                    }
                    leaf php {
                      xr:xr-xml-map "isis_cfg:PHP";
                      type Isisphp-flag;
                      mandatory true;
                      description
                        "Enable/Disable Penultimate Hop Popping";
                    }
                    leaf explicit-null {
                      xr:xr-xml-map "isis_cfg:EXPLICITNULL";
                      type Isisexplicit-null-flag;
                      mandatory true;
                      description
                        "Enable/Disable Explicit-NULL flag";
                    }
                    leaf nflag-clear {
                      xr:xr-xml-map "isis_cfg:NFlagClear";
                      type Nflag-clear;
                      mandatory true;
                      description "Clear N-flag for the prefix-SID";
                    }
                  }

                  container interface-frr-table {
                    xr:xr-xml-map "isis_cfg:InterfaceFRRTable";
                    description "Fast-ReRoute configuration";

                    container frrlfa-candidate-interfaces {
                      xr:xr-xml-map "isis_cfg:FRRLFACandidateTable";
                      description "FRR LFA candidate configuration";

                      list frrlfa-candidate-interface {
                        xr:xr-xml-map "isis_cfg:FRRLFACandidateInte"+
                          "rface";
                        key "interface-name frr-type";
                        description
                          "Include an interface to LFA candidate
                          in computation";
                        leaf interface-name {
                          xr:xr-xml-map "isis_cfg:InterfaceName";
                          type xr:Interface-name;
                          description "Interface";
                        }
                        leaf frr-type {
                          xr:xr-xml-map "isis_cfg:FRRType";
                          type Isisfrr;
                          description "Computation Type";
                        }
                        leaf level {
                          xr:xr-xml-map "isis_cfg:Level";
                          type uint32 {
                            range "0..2";
                          }
                          mandatory true;
                          description "Level";
                        }
                      }
                    }

                    container frr-remote-lfa-max-metrics {
                      xr:xr-xml-map "isis_cfg:FRRRemoteLFAMaxMetric"+
                        "Table";
                      description "Remote LFA maxmimum metric";

                      list frr-remote-lfa-max-metric {
                        xr:xr-xml-map "isis_cfg:FRRRemoteLFAMaxMetr"+
                          "ic";
                        key "level";
                        description
                          "Configure the maximum metric for
                          selecting a remote LFA node";
                        leaf level {
                          xr:xr-xml-map "isis_cfg:Level";
                          type dt1:Isis-internal-level;
                          description
                            "Level to which configuration applies";
                        }
                        leaf max-metric {
                          xr:xr-xml-map "isis_cfg:MaxMetric";
                          type uint32 {
                            range "1..16777215";
                          }
                          mandatory true;
                          description "Value of the metric";
                        }
                      }
                    }

                    container frr-types {
                      xr:xr-xml-map "isis_cfg:FRRTypeTable";
                      description
                        "Type of FRR computation per level";

                      list frr-type {
                        xr:xr-xml-map "isis_cfg:FRRType";
                        key "level";
                        description
                          "Type of computation for prefixes
                          reachable via interface";
                        leaf level {
                          xr:xr-xml-map "isis_cfg:Level";
                          type dt1:Isis-internal-level;
                          description
                            "Level to which configuration applies";
                        }
                        leaf type {
                          xr:xr-xml-map "isis_cfg:Type";
                          type Isisfrr;
                          mandatory true;
                          description "Computation Type";
                        }
                      }
                    }

                    container frr-remote-lfa-types {
                      xr:xr-xml-map "isis_cfg:FRRRemoteLFATypeTable";
                      description "Remote LFA Enable";

                      list frr-remote-lfa-type {
                        xr:xr-xml-map "isis_cfg:FRRRemoteLFAType";
                        key "level";
                        description
                          "Enable remote lfa for a particular
                          level";
                        leaf level {
                          xr:xr-xml-map "isis_cfg:Level";
                          type dt1:Isis-internal-level;
                          description
                            "Level to which configuration applies";
                        }
                        leaf type {
                          xr:xr-xml-map "isis_cfg:Type";
                          type Isis-remote-lfa;
                          mandatory true;
                          description "Remote LFA Type";
                        }
                      }
                    }

                    container interface-frr-tiebreaker-defaults {
                      xr:xr-xml-map "isis_cfg:InterfaceDefaultFRRTi"+
                        "ebreakerTable";
                      description
                        "Interface FRR Default tiebreaker
                        configuration";

                      list interface-frr-tiebreaker-default {
                        xr:xr-xml-map "isis_cfg:InterfaceFRRTiebrea"+
                          "kerDefault";
                        key "level";
                        description "Configure default tiebreaker";
                        leaf level {
                          xr:xr-xml-map "isis_cfg:Level";
                          type dt1:Isis-internal-level;
                          description
                            "Level to which configuration applies";
                        }
                      }
                    }

                    container frrtilfa-types {
                      xr:xr-xml-map "isis_cfg:FRRTILFATypeTable";
                      description "TI LFA Enable";

                      list frrtilfa-type {
                        xr:xr-xml-map "isis_cfg:FRRTILFAType";
                        key "level";
                        description
                          "Enable TI lfa for a particular level";
                        leaf level {
                          xr:xr-xml-map "isis_cfg:Level";
                          type dt1:Isis-internal-level;
                          description
                            "Level to which configuration applies";
                        }
                      }
                    }

                    container frr-exclude-interfaces {
                      xr:xr-xml-map "isis_cfg:FRRExcludeTable";
                      description "FRR exclusion configuration";

                      list frr-exclude-interface {
                        xr:xr-xml-map "isis_cfg:FRRExcludeInterface";
                        key "interface-name frr-type";
                        description
                          "Exclude an interface from computation";
                        leaf interface-name {
                          xr:xr-xml-map "isis_cfg:InterfaceName";
                          type xr:Interface-name;
                          description "Interface";
                        }
                        leaf frr-type {
                          xr:xr-xml-map "isis_cfg:FRRType";
                          type Isisfrr;
                          description "Computation Type";
                        }
                        leaf level {
                          xr:xr-xml-map "isis_cfg:Level";
                          type uint32 {
                            range "0..2";
                          }
                          mandatory true;
                          description "Level";
                        }
                      }
                    }

                    container interface-frr-tiebreakers {
                      xr:xr-xml-map "isis_cfg:InterfaceFRRTiebreake"+
                        "rsTable";
                      description
                        "Interface FRR tiebreakers configuration";

                      list interface-frr-tiebreaker {
                        xr:xr-xml-map "isis_cfg:InterfaceFRRTiebrea"+
                          "ker";
                        key "level tiebreaker";
                        description
                          "Configure tiebreaker for multiple
                          backups";
                        leaf level {
                          xr:xr-xml-map "isis_cfg:Level";
                          type dt1:Isis-internal-level;
                          description
                            "Level to which configuration applies";
                        }
                        leaf tiebreaker {
                          xr:xr-xml-map "isis_cfg:Tiebreaker";
                          type Isis-interface-frr-tiebreaker;
                          description
                            "Tiebreaker for which configuration
                            applies";
                        }
                        leaf index {
                          xr:xr-xml-map "isis_cfg:Index";
                          type uint32 {
                            range "1..255";
                          }
                          mandatory true;
                          description
                            "Preference order among tiebreakers";
                        }
                      }
                    }
                  }

                  container mpls-ldp {
                    xr:xr-xml-map "isis_cfg:MPLS_LDP";
                    description "MPLS LDP configuration";
                    leaf sync-level {
                      xr:xr-xml-map "isis_cfg:SyncLevel";
                      type uint32 {
                        range "0..2";
                      }
                      default "0";
                      description
                        "Enable MPLS LDP Synchronization for an
                        IS-IS level";
                    }
                  }

                  container auto-metrics {
                    xr:xr-xml-map "isis_cfg:AutoMetricTable";
                    description "AutoMetric configuration";

                    list auto-metric {
                      xr:xr-xml-map "isis_cfg:AutoMetric";
                      key "level";
                      description
                        "AutoMetric Proactive-Protect
                        configuration. Legal value depends on
                        the metric-style specified for the
                        topology. If the metric-style defined is
                        narrow, then only a value between <1-63>
                        is allowed and if the metric-style is
                        defined as wide, then a value between
                        <1-16777214> is allowed as the
                        auto-metric value.";
                      leaf level {
                        xr:xr-xml-map "isis_cfg:Level";
                        type dt1:Isis-internal-level;
                        description
                          "Level to which configuration applies";
                      }
                      leaf proactive-protect {
                        xr:xr-xml-map "isis_cfg:ProactiveProtect";
                        type uint32 {
                          range "1..16777214";
                        }
                        mandatory true;
                        description
                          "Allowed auto metric:<1-63> for narrow
                          ,<1-16777214> for wide";
                      }
                    }
                  }

                  container admin-tags {
                    xr:xr-xml-map "isis_cfg:AdminTagTable";
                    description "admin-tag configuration";

                    list admin-tag {
                      xr:xr-xml-map "isis_cfg:AdminTag";
                      key "level";
                      description
                        "Admin tag for advertised interface
                        connected routes";
                      leaf level {
                        xr:xr-xml-map "isis_cfg:Level";
                        type dt1:Isis-internal-level;
                        description
                          "Level to which configuration applies";
                      }
                      leaf admin-tag {
                        xr:xr-xml-map "isis_cfg:AdminTag";
                        type uint32 {
                          range "1..4294967295";
                        }
                        mandatory true;
                        description
                          "Tag to associate with connected routes";
                      }
                    }
                  }

                  container interface-link-group {
                    xr:xr-xml-map "isis_cfg:InterfaceLinkGroup";
                    presence "Indicates a interface-link-group node"+
                      " is configured.";
                    description "Provide link group name and level";
                    leaf link-group {
                      xr:xr-xml-map "isis_cfg:LinkGroup";
                      type dt1:Isis-link-group-name;
                      mandatory true;
                      description "Link Group";
                    }
                    leaf level {
                      xr:xr-xml-map "isis_cfg:Level";
                      type uint32 {
                        range "0..2";
                      }
                      default "0";
                      description
                        "Level in which link group will be
                        effective";
                    }
                  }
                  leaf interface-af-state {
                    xr:xr-xml-map "isis_cfg:InterfaceAFState";
                    type Isis-interface-af-state;
                    description "Interface state";
                  }
                  leaf running {
                    xr:xr-xml-map "isis_cfg:Running";
                    type empty;
                    description
                      "The presence of this object allows an
                      address-family to be run over the
                      interface in question.This must be the
                      first object created under the
                      InterfaceAddressFamily container, and the
                      last one deleted";
                  }
                  uses METRIC-TABLE;
                  uses WEIGHT-TABLE;
                }

                container interface-af-data {
                  xr:xr-xml-map "isis_cfg:InterfaceAF";
                  description "Data container.";
                  uses INTERFACE-AF-CONTENT;
                }
                leaf af-name {
                  xr:xr-xml-map "isis_cfg:AFName";
                  type dt1:Isis-address-family;
                  description "Address family";
                }
                leaf saf-name {
                  xr:xr-xml-map "isis_cfg:SAFName";
                  type dt1:Isis-sub-address-family;
                  description "Sub address family";
                }

                list topology-name {
                  xr:xr-xml-map "isis_cfg:InterfaceAF";
                  key "topology-name";
                  description "keys: topology-name";
                  leaf topology-name {
                    xr:xr-xml-map "isis_cfg:TopologyName";
                    type dt1:Isis-topology-name;
                    description "Topology Name";
                  }
                  uses INTERFACE-AF-CONTENT;
                }
              }
            }

            container csnp-intervals {
              xr:xr-xml-map "isis_cfg:CSNPIntervalTable";
              description "CSNP-interval configuration";

              list csnp-interval {
                xr:xr-xml-map "isis_cfg:CSNPInterval";
                xr:xr-cli-map "isis <string> interface <interface> "+
                  "csnp-interval <number> [level <number>] ";
                key "level";
                description
                  "CSNP-interval configuration. No fixed
                  default value as this depends on the media
                  type of the interface.";
                leaf level {
                  xr:xr-xml-map "isis_cfg:Level";
                  type dt1:Isis-internal-level;
                  description
                    "Level to which configuration applies";
                }
                leaf interval {
                  xr:xr-xml-map "isis_cfg:Interval";
                  type uint32 {
                    range "0..65535";
                  }
                  units "second";
                  mandatory true;
                  description "Seconds";
                }
              }
            }

            container lsp-intervals {
              xr:xr-xml-map "isis_cfg:LSPIntervalTable";
              description "LSP-interval configuration";

              list lsp-interval {
                xr:xr-xml-map "isis_cfg:LSPInterval";
                xr:xr-cli-map "isis <string> interface <interface> "+
                  "lsp-interval <number> [level <number>] ";
                key "level";
                description
                  "Interval between transmission of LSPs on
                  interface.";
                leaf level {
                  xr:xr-xml-map "isis_cfg:Level";
                  type dt1:Isis-internal-level;
                  description
                    "Level to which configuration applies";
                }
                leaf interval {
                  xr:xr-xml-map "isis_cfg:Interval";
                  type uint32 {
                    range "1..4294967295";
                  }
                  units "millisecond";
                  mandatory true;
                  description "Milliseconds";
                }
              }
            }
            leaf running {
              xr:xr-xml-map "isis_cfg:Running";
              type empty;
              description
                "This object must be set before any other
                configuration is supplied for an interface,
                and must be the last per-interface
                configuration object to be removed.";
            }
            leaf circuit-type {
              xr:xr-xml-map "isis_cfg:CircuitType";
              xr:xr-cli-map "isis <string> interface <interface> ci"+
                "rcuit-type <enum> ";
              type Isis-configurable-levels;
              default "level1-and2";
              description "Configure circuit type for interface";
            }
            leaf point-to-point {
              xr:xr-xml-map "isis_cfg:PointToPoint";
              xr:xr-cli-map "isis <string> interface <interface> po"+
                "int-to-point ";
              type empty;
              description
                "IS-IS will attempt to form point-to-point
                over LAN adjacencies over this interface.";
            }
            leaf state {
              xr:xr-xml-map "isis_cfg:State";
              xr:xr-cli-map "isis <string> interface <interface> (p"+
                "assive)|(suppressed)|(disable)|(shutdown) ";
              type Isis-interface-state;
              description "Enable/Disable routing";
            }
            leaf mesh-group {
              xr:xr-xml-map "isis_cfg:MeshGroup";
              xr:xr-cli-map "isis <string> interface <interface> me"+
                "sh-group (<number>)|(blocked) ";
              type union {
                type enumeration {
                  enum blocked {
                    value 0;
                    description
                      "Blocked mesh group.  Changed LSPs are not
                      flooded over blocked interfaces";
                  }
                }
                type uint32 {
                  range "0..4294967295";
                }
              }
              description "Mesh-group configuration";
            }
            leaf link-down-fast-detect {
              xr:xr-xml-map "isis_cfg:LinkDownFastDetect";
              xr:xr-cli-map "isis <string> interface <interface> li"+
                "nk-down fast-detect ";
              type empty;
              description
                "Configure high priority detection of
                interface down event";
            }
            leaf interface-name {
              xr:xr-xml-map "isis_cfg:InterfaceName";
              type xr:Interface-name;
              description "Interface name";
            }
          }
        }
        leaf running {
          xr:xr-xml-map "isis_cfg:Running";
          type empty;
          description
            "Flag to indicate that instance should be
            running.  This must be the first object
            created when an IS-IS instance is configured,
            and the last object deleted when it is
            deconfigured.  When this object is deleted,
            the IS-IS instance will exit.";
        }
        leaf log-adjacency-changes {
          xr:xr-xml-map "isis_cfg:LogAdjacencyChanges";
          xr:xr-cli-map "isis <string> log-adjacency-changes ";
          type empty;
          description "Log changes in adjacency state";
        }
        leaf ignore-lsp-errors {
          xr:xr-xml-map "isis_cfg:IgnoreLSPErrors";
          xr:xr-cli-map "isis <string> ignore-lsp-errors (enable)|("+
            "disable) ";
          type boolean;
          description
            "If TRUE, LSPs recieved with bad checksums will
            result in the purging of that LSP from the LSP
            DB. If FALSE or not set, the received LSP will
            just be ignored.";
        }
        leaf is-type {
          xr:xr-xml-map "isis_cfg:ISType";
          xr:xr-cli-map "isis <string> is-type <enum> ";
          type Isis-configurable-levels;
          default "level1-and2";
          description "IS type of the IS-IS process";
        }
        leaf tracing-mode {
          xr:xr-xml-map "isis_cfg:TracingMode";
          xr:xr-cli-map "isis <string> trace mode <enum> ";
          type Isis-tracing-mode;
          default "basic";
          description "Tracing mode configuration";
        }
        leaf instance-id {
          xr:xr-xml-map "isis_cfg:InstanceID";
          xr:xr-cli-map "isis <string> instance-id <number> ";
          type uint32 {
            range "0..65535";
          }
          default "0";
          description "Instance ID of the IS-IS process";
        }
        leaf dynamic-host-name {
          xr:xr-xml-map "isis_cfg:DynamicHostname";
          xr:xr-cli-map "isis <string> hostname dynamic (enable)|(d"+
            "isable) ";
          type boolean;
          description
            "If TRUE, dynamic hostname resolution is
            disabled, and system IDs will always be
            displayed by show and debug output.";
        }
        leaf nsr {
          xr:xr-xml-map "isis_cfg:NSR";
          xr:xr-cli-map "isis <string> nsr ";
          type empty;
          description "IS-IS NSR configuration";
        }
        leaf log-pdu-drops {
          xr:xr-xml-map "isis_cfg:LogPDUDrops";
          xr:xr-cli-map "isis <string> log pdu drops ";
          type empty;
          description "Log PDU drops";
        }
        leaf instance-name {
          xr:xr-xml-map "isis_cfg:InstanceName";
          type dt1:Isis-instance-name;
          description "Instance identifier";
        }
      }
    }
  }

  augment "/a1:snmp/a1:notification" {

    container isis {
      xr:xr-xml-map "isismib_cfg:ISIS";
      description "Enable ISIS-MIB notifications";
      leaf database-overflow {
        xr:xr-xml-map "isismib_cfg:DatabaseOverflow";
        type Isis-mib-database-over-flow-boolean;
        default "false";
        description "Enable or disable";
      }
      leaf manual-address-drops {
        xr:xr-xml-map "isismib_cfg:ManualAddressDrops";
        type Isis-mib-manual-address-drops-boolean;
        default "false";
        description "Enable or disable";
      }
      leaf corrupted-lsp-detected {
        xr:xr-xml-map "isismib_cfg:CorruptedLSPDetected";
        type Isis-mib-corrupted-lsp-detected-boolean;
        default "false";
        description "Enable or disable";
      }
      leaf attempt-to-exceed-max-sequence {
        xr:xr-xml-map "isismib_cfg:AttemptToExceedMaxSequence";
        type Isis-mib-attempt-to-exceed-max-sequence-boolean;
        default "false";
        description "Enable or disable";
      }
      leaf id-length-mismatch {
        xr:xr-xml-map "isismib_cfg:IDLengthMismatch";
        type Isis-mib-id-length-mismatch-boolean;
        default "false";
        description "Enable or disable";
      }
      leaf max-area-address-mismatch {
        xr:xr-xml-map "isismib_cfg:MaxAreaAddressMismatch";
        type Isis-mib-max-area-address-mismatch-boolean;
        default "false";
        description "Enable or disable";
      }
      leaf own-lsp-purge {
        xr:xr-xml-map "isismib_cfg:OwnLSPPurge";
        type Isis-mib-own-lsp-purge-boolean;
        default "false";
        description "Enable or disable";
      }
      leaf sequence-number-skip {
        xr:xr-xml-map "isismib_cfg:SequenceNumberSkip";
        type Isis-mib-sequence-number-skip-boolean;
        default "false";
        description "Enable or disable";
      }
      leaf authentication-type-failure {
        xr:xr-xml-map "isismib_cfg:AuthenticationTypeFailure";
        type Isis-mib-authentication-type-failure-boolean;
        default "false";
        description "Enable or disable";
      }
      leaf authentication-failure {
        xr:xr-xml-map "isismib_cfg:AuthenticationFailure";
        type Isis-mib-authentication-failure-boolean;
        default "false";
        description "Enable or disable";
      }
      leaf version-skew {
        xr:xr-xml-map "isismib_cfg:VersionSkew";
        type Isis-mib-version-skew-boolean;
        default "false";
        description "Enable or disable";
      }
      leaf area-mismatch {
        xr:xr-xml-map "isismib_cfg:AreaMismatch";
        type Isis-mib-area-mismatch-boolean;
        default "false";
        description "Enable or disable";
      }
      leaf rejected-adjacency {
        xr:xr-xml-map "isismib_cfg:RejectedAdjacency";
        type Isis-mib-rejected-adjacency-boolean;
        default "false";
        description "Enable or disable";
      }
      leaf lsp-too-large-to-propagate {
        xr:xr-xml-map "isismib_cfg:LSPTooLargeToPropagate";
        type Isis-mib-lsp-too-large-to-propagate-boolean;
        default "false";
        description "Enable or disable";
      }
      leaf originated-lsp-buffer-size-mismatch {
        xr:xr-xml-map "isismib_cfg:OriginatedLSPBufferSizeMismatch";
        type Isis-mib-originated-lsp-buffer-size-mismatch-boolean;
        default "false";
        description "Enable or disable";
      }
      leaf protocols-supported-mismatch {
        xr:xr-xml-map "isismib_cfg:ProtocolsSupportedMismatch";
        type Isis-mib-protocols-supported-mismatch-boolean;
        default "false";
        description "Enable or disable";
      }
      leaf adjacency-change {
        xr:xr-xml-map "isismib_cfg:AdjacencyChange";
        type Isis-mib-adjacency-change-boolean;
        default "false";
        description "Enable or disable";
      }
      leaf lsp-error-detected {
        xr:xr-xml-map "isismib_cfg:LSPErrorDetected";
        type Isis-mib-lsp-error-detected-boolean;
        default "false";
        description "Enable or disable";
      }
      leaf all {
        xr:xr-xml-map "isismib_cfg:All";
        type Isis-mib-all-boolean;
        default "false";
        description "Enable all isisMIB notifications";
      }
    }
    description
      "This augment extends the configuration data of
      'Cisco-IOS-XR-snmp-agent-cfg'";
  }
}
