module Cisco-IOS-XR-config-mda-cfg {

  /*** NAMESPACE / PREFIX DEFINITION ***/

  namespace "http://cisco.com/ns/yang/Cisco-IOS-XR-config-mda-cfg";


  prefix "config-mda-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR config-mda package configuration.

     This module contains definitions
     for the following management objects:
       apply-group: Apply configuration from a group
       exclude-group: exclude group
       apply-group-remove: apply group remove
       active-nodes: active nodes
       apply-group-append: apply group append
       groups: groups
       preconfigured-nodes: preconfigured nodes

     Copyright (c) 2013-2016 by Cisco Systems, Inc.
     All rights reserved.";

  revision "2015-11-09" {
    description
      "IOS XR 6.0 revision.";
  }


  container apply-group {
    xr:xr-xml-map "mda_common_cfg:ApplyGroup";
    presence "Indicates a apply-group node is configured.";
    description "Apply configuration from a group";
    leaf group1 {
      xr:xr-xml-map "mda_common_cfg:group1";
      type string;
      mandatory true;
      description "Group name";
    }
    leaf group2 {
      xr:xr-xml-map "mda_common_cfg:group2";
      type string;
      description "Group name";
    }
    leaf group3 {
      xr:xr-xml-map "mda_common_cfg:group3";
      type string;
      description "Group name";
    }
    leaf group4 {
      xr:xr-xml-map "mda_common_cfg:group4";
      type string;
      description "Group name";
    }
    leaf group5 {
      xr:xr-xml-map "mda_common_cfg:group5";
      type string;
      description "Group name";
    }
    leaf group6 {
      xr:xr-xml-map "mda_common_cfg:group6";
      type string;
      description "Group name";
    }
    leaf group7 {
      xr:xr-xml-map "mda_common_cfg:group7";
      type string;
      description "Group name";
    }
    leaf group8 {
      xr:xr-xml-map "mda_common_cfg:group8";
      type string;
      description "Group name";
    }
  }

  container exclude-group {
    xr:xr-xml-map "mda_common_cfg:ExcludeGroup";
    presence "Indicates a exclude-group node is configured.";
    description "exclude group";
    leaf group1 {
      xr:xr-xml-map "mda_common_cfg:group1";
      type string;
      mandatory true;
      description "Group name";
    }
    leaf group2 {
      xr:xr-xml-map "mda_common_cfg:group2";
      type string;
      description "Group name";
    }
    leaf group3 {
      xr:xr-xml-map "mda_common_cfg:group3";
      type string;
      description "Group name";
    }
    leaf group4 {
      xr:xr-xml-map "mda_common_cfg:group4";
      type string;
      description "Group name";
    }
    leaf group5 {
      xr:xr-xml-map "mda_common_cfg:group5";
      type string;
      description "Group name";
    }
    leaf group6 {
      xr:xr-xml-map "mda_common_cfg:group6";
      type string;
      description "Group name";
    }
    leaf group7 {
      xr:xr-xml-map "mda_common_cfg:group7";
      type string;
      description "Group name";
    }
    leaf group8 {
      xr:xr-xml-map "mda_common_cfg:group8";
      type string;
      description "Group name";
    }
  }

  container apply-group-remove {
    xr:xr-xml-map "mda_common_cfg:ApplyGroupRemove";
    presence "Indicates a apply-group-remove node is configured.";
    description "apply group remove";
    leaf group1 {
      xr:xr-xml-map "mda_common_cfg:group1";
      type string;
      mandatory true;
      description "Group name";
    }
    leaf group2 {
      xr:xr-xml-map "mda_common_cfg:group2";
      type string;
      description "Group name";
    }
    leaf group3 {
      xr:xr-xml-map "mda_common_cfg:group3";
      type string;
      description "Group name";
    }
    leaf group4 {
      xr:xr-xml-map "mda_common_cfg:group4";
      type string;
      description "Group name";
    }
    leaf group5 {
      xr:xr-xml-map "mda_common_cfg:group5";
      type string;
      description "Group name";
    }
    leaf group6 {
      xr:xr-xml-map "mda_common_cfg:group6";
      type string;
      description "Group name";
    }
    leaf group7 {
      xr:xr-xml-map "mda_common_cfg:group7";
      type string;
      description "Group name";
    }
    leaf group8 {
      xr:xr-xml-map "mda_common_cfg:group8";
      type string;
      description "Group name";
    }
  }

  container active-nodes {
    xr:xr-xml-map "mda_common_cfg:ActiveNodeTable";
    description "active nodes";

    list active-node {
      xr:xr-xml-map "mda_common_cfg:ActiveNode";
      key "node-name";
      description "The configuration for an active node";
      leaf node-name {
        xr:xr-xml-map "mda_common_cfg:NodeName";
        type xr:Node-id;
        description "The identifier for this node";
      }
    }
  }

  container apply-group-append {
    xr:xr-xml-map "mda_common_cfg:ApplyGroupAppend";
    presence "Indicates a apply-group-append node is configured.";
    description "apply group append";
    leaf group1 {
      xr:xr-xml-map "mda_common_cfg:group1";
      type string;
      mandatory true;
      description "Group name";
    }
    leaf group2 {
      xr:xr-xml-map "mda_common_cfg:group2";
      type string;
      description "Group name";
    }
    leaf group3 {
      xr:xr-xml-map "mda_common_cfg:group3";
      type string;
      description "Group name";
    }
    leaf group4 {
      xr:xr-xml-map "mda_common_cfg:group4";
      type string;
      description "Group name";
    }
    leaf group5 {
      xr:xr-xml-map "mda_common_cfg:group5";
      type string;
      description "Group name";
    }
    leaf group6 {
      xr:xr-xml-map "mda_common_cfg:group6";
      type string;
      description "Group name";
    }
    leaf group7 {
      xr:xr-xml-map "mda_common_cfg:group7";
      type string;
      description "Group name";
    }
    leaf group8 {
      xr:xr-xml-map "mda_common_cfg:group8";
      type string;
      description "Group name";
    }
  }

  container groups {
    xr:xr-xml-map "mda_common_cfg:GroupTable";
    description "groups";

    list group {
      xr:xr-xml-map "mda_common_cfg:Group";
      key "group-name";
      description "configuration for a group";
      leaf create {
        xr:xr-xml-map "mda_common_cfg:Create";
        type empty;
        description "Create this group";
      }
      leaf group-name {
        xr:xr-xml-map "mda_common_cfg:GroupName";
        type xr:Cisco-ios-xr-string {
          length "0..32";
        }
        description "The identifier for this group";
      }
    }
  }

  container preconfigured-nodes {
    xr:xr-xml-map "mda_common_cfg:PreconfiguredNodeTable";
    description "preconfigured nodes";

    list preconfigured-node {
      xr:xr-xml-map "mda_common_cfg:PreconfiguredNode";
      key "node-name";
      description "The configuration for a non-active node";
      leaf node-name {
        xr:xr-xml-map "mda_common_cfg:NodeName";
        type xr:Node-id;
        description "The identifier for this node";
      }
    }
  }
}
