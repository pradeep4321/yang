submodule Cisco-IOS-XR-dnx-driver-oper-sub1 {

  belongs-to Cisco-IOS-XR-dnx-driver-oper {
    prefix Cisco-IOS-XR-dnx-driver-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR dnx-driver package operational data.

     Copyright (c) 2013-2016 by Cisco Systems, Inc.
     All rights reserved.";

  revision "2015-11-09" {
    description
      "IOS XR 6.0 revision.";
  }


  grouping FIA-EDM-LINK-OVF-COUNTERS {
    description "FIA EDM LINK OVF COUNTERS";
    leaf tx-control-cells-counter {
      xr:xr-xml-map "fia_edm_defs:TX_Control_cells_counter";
      type string {
        length "0..6";
      }
      description "TX Control cells counter";
    }
    leaf tx-data-cell-counter {
      xr:xr-xml-map "fia_edm_defs:TX_Data_cell_counter";
      type string {
        length "0..6";
      }
      description "TX Data cell counter";
    }
    leaf tx-data-byte-counter {
      xr:xr-xml-map "fia_edm_defs:TX_Data_byte_counter";
      type string {
        length "0..6";
      }
      description "TX Data byte counter";
    }
    leaf rx-crc-errors-counter {
      xr:xr-xml-map "fia_edm_defs:RX_CRC_errors_counter";
      type string {
        length "0..6";
      }
      description "RX CRC errors counter";
    }
    leaf rx-lfec-fec-correctable-error {
      xr:xr-xml-map "fia_edm_defs:RX_LFEC_FEC_correctable_error";
      type string {
        length "0..6";
      }
      description "RX LFEC FEC correctable error";
    }
    leaf rx-8b-10b-disparity-errors {
      xr:xr-xml-map "fia_edm_defs:RX_8b_10b_disparity_errors";
      type string {
        length "0..6";
      }
      description "RX 8b 10b disparity errors";
    }
    leaf rx-control-cells-counter {
      xr:xr-xml-map "fia_edm_defs:RX_Control_cells_counter";
      type string {
        length "0..6";
      }
      description "RX Control cells counter";
    }
    leaf rx-data-cell-counter {
      xr:xr-xml-map "fia_edm_defs:RX_Data_cell_counter";
      type string {
        length "0..6";
      }
      description "RX Data cell counter";
    }
    leaf rx-data-byte-counter {
      xr:xr-xml-map "fia_edm_defs:RX_Data_byte_counter";
      type string {
        length "0..6";
      }
      description "RX Data byte counter";
    }
    leaf rx-dropped-retransmitted-control {
      xr:xr-xml-map "fia_edm_defs:RX_dropped_retransmitted_control";
      type string {
        length "0..6";
      }
      description "RX dropped retransmitted control";
    }
    leaf tx-asyn-fifo-rate {
      xr:xr-xml-map "fia_edm_defs:TX_Asyn_fifo_rate";
      type string {
        length "0..6";
      }
      description "TX Asyn fifo rate";
    }
    leaf rx-asyn-fifo-rate {
      xr:xr-xml-map "fia_edm_defs:RX_Asyn_fifo_rate";
      type string {
        length "0..6";
      }
      description "RX Asyn fifo rate";
    }
    leaf rx-lfec-fec-uncorrectable-errors {
      xr:xr-xml-map "fia_edm_defs:RX_LFEC_FEC_uncorrectable_errors";
      type string {
        length "0..6";
      }
      description "RX LFEC FEC uncorrectable errors";
    }
    leaf rx-8b-10b-code-errors {
      xr:xr-xml-map "fia_edm_defs:RX_8b_10b_code_errors";
      type string {
        length "0..6";
      }
      description "RX 8b 10b code errors";
    }
  }

  grouping FIA-EDM-LINK-COUNTERS {
    description "FIA EDM LINK COUNTERS";
    leaf tx-control-cells-counter {
      xr:xr-xml-map "fia_edm_defs:TX_Control_cells_counter";
      type uint64;
      description "TX Control cells counter";
    }
    leaf tx-data-cell-counter {
      xr:xr-xml-map "fia_edm_defs:TX_Data_cell_counter";
      type uint64;
      description "TX Data cell counter";
    }
    leaf tx-data-byte-counter {
      xr:xr-xml-map "fia_edm_defs:TX_Data_byte_counter";
      type uint64;
      description "TX Data byte counter";
    }
    leaf rx-crc-errors-counter {
      xr:xr-xml-map "fia_edm_defs:RX_CRC_errors_counter";
      type uint64;
      description "RX CRC errors counter";
    }
    leaf rx-lfec-fec-correctable-error {
      xr:xr-xml-map "fia_edm_defs:RX_LFEC_FEC_correctable_error";
      type uint64;
      description "RX LFEC FEC correctable error";
    }
    leaf rx-8b-10b-disparity-errors {
      xr:xr-xml-map "fia_edm_defs:RX_8b_10b_disparity_errors";
      type uint64;
      description "RX 8b 10b disparity errors";
    }
    leaf rx-control-cells-counter {
      xr:xr-xml-map "fia_edm_defs:RX_Control_cells_counter";
      type uint64;
      description "RX Control cells counter";
    }
    leaf rx-data-cell-counter {
      xr:xr-xml-map "fia_edm_defs:RX_Data_cell_counter";
      type uint64;
      description "RX Data cell counter";
    }
    leaf rx-data-byte-counter {
      xr:xr-xml-map "fia_edm_defs:RX_Data_byte_counter";
      type uint64;
      description "RX Data byte counter";
    }
    leaf rx-dropped-retransmitted-control {
      xr:xr-xml-map "fia_edm_defs:RX_dropped_retransmitted_control";
      type uint64;
      description "RX dropped retransmitted control";
    }
    leaf tx-asyn-fifo-rate {
      xr:xr-xml-map "fia_edm_defs:TX_Asyn_fifo_rate";
      type uint64;
      description "TX Asyn fifo rate";
    }
    leaf rx-asyn-fifo-rate {
      xr:xr-xml-map "fia_edm_defs:RX_Asyn_fifo_rate";
      type uint64;
      description "RX Asyn fifo rate";
    }
    leaf rx-lfec-fec-uncorrectable-errors {
      xr:xr-xml-map "fia_edm_defs:RX_LFEC_FEC_uncorrectable_errors";
      type uint64;
      description "RX LFEC FEC uncorrectable errors";
    }
    leaf rx-8b-10b-code-errors {
      xr:xr-xml-map "fia_edm_defs:RX_8b_10b_code_errors";
      type uint64;
      description "RX 8b 10b code errors";
    }
  }

  grouping FIA-EDM-LINK-ERROR-STATUS {
    description "FIA EDM LINK ERROR STATUS";
    leaf link-crc-error {
      xr:xr-xml-map "fia_edm_defs:link_crc_error";
      type uint32;
      description "link crc error";
    }
    leaf link-size-error {
      xr:xr-xml-map "fia_edm_defs:link_size_error";
      type uint32;
      description "link size error";
    }
    leaf link-mis-align-error {
      xr:xr-xml-map "fia_edm_defs:link_mis_align_error";
      type uint32;
      description "link mis align error";
    }
    leaf link-code-group-error {
      xr:xr-xml-map "fia_edm_defs:link_code_group_error";
      type uint32;
      description "link code group error";
    }
    leaf link-no-sig-lock-error {
      xr:xr-xml-map "fia_edm_defs:link_no_sig_lock_error";
      type uint32;
      description "link no sig lock error";
    }
    leaf link-no-sig-accept-error {
      xr:xr-xml-map "fia_edm_defs:link_no_sig_accept_error";
      type uint32;
      description "link no sig accept error";
    }
    leaf link-tokens-error {
      xr:xr-xml-map "fia_edm_defs:link_tokens_error";
      type uint32;
      description "link tokens error";
    }
    leaf error-token-count {
      xr:xr-xml-map "fia_edm_defs:error_token_count";
      type uint32;
      description "error token count";
    }
  }

  grouping FIA-EDM-STATS-ASIC-FMAC {
    description "FIA EDM STATS ASIC FMAC";

    container link-error-status {
      description "link error status";
      uses FIA-EDM-LINK-ERROR-STATUS;
    }

    container link-counters {
      description "link counters";
      uses FIA-EDM-LINK-COUNTERS;
    }

    container ovf-status {
      description "ovf status";
      uses FIA-EDM-LINK-OVF-COUNTERS;
    }
  }

  grouping FIA-EDM-STATS-ASIC-FMAC-INFO {
    description "FIA EDM STATS ASIC FMAC INFO";

    container aggr-stats {
      description "aggr stats";
      uses FIA-EDM-STATS-ASIC-FMAC;
    }

    container incr-stats {
      description "incr stats";
      uses FIA-EDM-STATS-ASIC-FMAC;
    }
    leaf valid {
      xr:xr-xml-map "fia_edm_defs:valid";
      type boolean;
      description "valid";
    }
    leaf rack-no {
      xr:xr-xml-map "fia_edm_defs:rack_no";
      type uint32;
      description "rack no";
    }
    leaf slot-no {
      xr:xr-xml-map "fia_edm_defs:slot_no";
      type uint32;
      description "slot no";
    }
    leaf asic-instance {
      xr:xr-xml-map "fia_edm_defs:asic_instance";
      type uint32;
      description "asic instance";
    }
    leaf link-no {
      xr:xr-xml-map "fia_edm_defs:link_no";
      type uint32;
      description "link no";
    }
    leaf link-valid {
      xr:xr-xml-map "fia_edm_defs:link_valid";
      type boolean;
      description "link valid";
    }
  }

  grouping FIA-EDM-DEVICE-STATS-FIELD-INFO {
    description "FIA EDM DEVICE STATS FIELD INFO";
    leaf field-name {
      xr:xr-xml-map "fia_edm_defs:Field_Name";
      type string {
        length "0..51";
      }
      description "Field Name";
    }
    leaf field-value {
      xr:xr-xml-map "fia_edm_defs:Field_Value";
      type uint64;
      description "Field Value";
    }
    leaf is-ovf {
      xr:xr-xml-map "fia_edm_defs:Is_Ovf";
      type boolean;
      description "Is Ovf";
    }
  }

  grouping FIA-EDM-DEVICE-STATS-BLK-INFO {
    description "FIA EDM DEVICE STATS BLK INFO";
    leaf block-name {
      xr:xr-xml-map "fia_edm_defs:Block_Name";
      type string {
        length "0..11";
      }
      description "Block Name";
    }
    leaf num-fields {
      xr:xr-xml-map "fia_edm_defs:Num_Fields";
      type uint8;
      description "Num Fields";
    }

    list field-info {
      max-elements "200";
      description "field info";
      uses FIA-EDM-DEVICE-STATS-FIELD-INFO;
    }
  }

  grouping FIA-EDM-DEVICE-STATS-ASIC-INFO {
    description "FIA EDM DEVICE STATS ASIC INFO";
    leaf num-blocks {
      xr:xr-xml-map "fia_edm_defs:Num_Blocks";
      type uint8;
      description "Num Blocks";
    }

    list block-info {
      max-elements "15";
      description "block info";
      uses FIA-EDM-DEVICE-STATS-BLK-INFO;
    }
  }

  grouping FIA-EDM-STATS-INFO {
    description "FIA EDM STATS INFO";

    container stats-info {
      description "stats info";
      uses FIA-EDM-DEVICE-STATS-ASIC-INFO;
    }
    leaf valid {
      xr:xr-xml-map "fia_edm_defs:valid";
      type boolean;
      description "valid";
    }
    leaf rack-no {
      xr:xr-xml-map "fia_edm_defs:rack_no";
      type uint32;
      description "rack no";
    }
    leaf slot-no {
      xr:xr-xml-map "fia_edm_defs:slot_no";
      type uint32;
      description "slot no";
    }
    leaf asic-instance {
      xr:xr-xml-map "fia_edm_defs:asic_instance";
      type uint32;
      description "asic instance";
    }
    leaf chip-ver {
      xr:xr-xml-map "fia_edm_defs:chip_ver";
      type uint16;
      description "chip ver";
    }
  }

  grouping FIA-EDM-DIAG-SHELL-OUTPUT {
    description "FIA EDM DIAG SHELL OUTPUT";
    leaf output-xr {
      xr:xr-xml-map "fia_edm_defs:output-xr";
      type string;
      description "output xr";
    }
  }

  grouping FIA-EDM-REG-INFO {
    description "FIA EDM REG INFO";
    leaf output {
      xr:xr-xml-map "fia_edm_defs:output";
      type string;
      description "output";
    }
  }

  grouping FIA-EDM-TXLINK-STATS {
    description "FIA EDM TXLINK STATS";
    leaf dummy {
      xr:xr-xml-map "fia_edm_defs:dummy";
      type uint32;
      description "dummy";
    }
  }

  grouping FIA-EDM-TXLINK {
    description "FIA EDM TXLINK";

    container this-link {
      description "this link";
      uses FIA-EDM-LINK-IDENTITY;
    }

    container far-end-link {
      description "far end link";
      uses FIA-EDM-LINK-IDENTITY;
    }

    container stats {
      description "stats";
      uses FIA-EDM-TXLINK-STATS;
    }

    container history {
      description "history";
      uses FIA-EDM-HISTORY;
    }
    leaf speed {
      xr:xr-xml-map "fia_edm_defs:speed";
      type uint32;
      description "speed";
    }
    leaf stage {
      xr:xr-xml-map "fia_edm_defs:stage";
      type uint8;
      description "stage";
    }
    leaf is-link-valid {
      xr:xr-xml-map "fia_edm_defs:is_link_valid";
      type boolean;
      description "is link valid";
    }
    leaf is-conf-pending {
      xr:xr-xml-map "fia_edm_defs:is_conf_pending";
      type boolean;
      description "is conf pending";
    }
    leaf is-power-enabled {
      xr:xr-xml-map "fia_edm_defs:is_power_enabled";
      type boolean;
      description "is power enabled";
    }
    leaf coeff1 {
      xr:xr-xml-map "fia_edm_defs:coeff1";
      type uint32;
      description "coeff1";
    }
    leaf coeff2 {
      xr:xr-xml-map "fia_edm_defs:coeff2";
      type uint32;
      description "coeff2";
    }
    leaf admin-state {
      xr:xr-xml-map "fia_edm_defs:admin_state";
      type uint8;
      description "admin state";
    }
    leaf oper-state {
      xr:xr-xml-map "fia_edm_defs:oper_state";
      type uint8;
      description "oper state";
    }
    leaf error-state {
      xr:xr-xml-map "fia_edm_defs:error_state";
      type uint8;
      description "error state";
    }
    leaf num-admin-shuts {
      xr:xr-xml-map "fia_edm_defs:num_admin_shuts";
      type uint32;
      description "num admin shuts";
    }
  }

  grouping FIA-EDM-OIR-HISTORY {
    description "FIA EDM OIR HISTORY";
    leaf card-flag {
      xr:xr-xml-map "fia_edm_defs:card_flag";
      type int32;
      description "card flag";
    }
    leaf card-type {
      xr:xr-xml-map "fia_edm_defs:card_type";
      type int32;
      description "card type";
    }
    leaf reg-flag {
      xr:xr-xml-map "fia_edm_defs:reg_flag";
      type int32;
      description "reg flag";
    }
    leaf evt-flag {
      xr:xr-xml-map "fia_edm_defs:evt_flag";
      type int32;
      description "evt flag";
    }
    leaf rack-num {
      xr:xr-xml-map "fia_edm_defs:rack_num";
      type int32;
      description "rack num";
    }
    leaf instance {
      xr:xr-xml-map "fia_edm_defs:instance";
      type int32;
      description "instance";
    }
    leaf cur-card-state {
      xr:xr-xml-map "fia_edm_defs:cur_card_state";
      type int32;
      description "cur card state";
    }
  }

  grouping FIA-EDM-OIR-RECORD-CIRCULAR-BUFFER {
    description "FIA EDM OIR RECORD CIRCULAR BUFFER";
    leaf count {
      xr:xr-xml-map "fia_edm_defs:count";
      type int32;
      description "count";
    }
    leaf start {
      xr:xr-xml-map "fia_edm_defs:start";
      type int32;
      description "start";
    }
    leaf end {
      xr:xr-xml-map "fia_edm_defs:end";
      type int32;
      description "end";
    }

    list fia-oir-info {
      max-elements "10";
      description "fia oir info";
      uses FIA-EDM-OIR-HISTORY;
    }
  }

  grouping FIA-EDM-CARD-INFO {
    description "FIA EDM CARD INFO";

    container oir-circular-buffer {
      description "oir circular buffer";
      uses FIA-EDM-OIR-RECORD-CIRCULAR-BUFFER;
    }
    leaf card-type {
      xr:xr-xml-map "fia_edm_defs:card_type";
      type int32;
      description "card type";
    }
    leaf card-name {
      xr:xr-xml-map "fia_edm_defs:card_name";
      type string;
      description "card name";
    }
    leaf slot-no {
      xr:xr-xml-map "fia_edm_defs:slot_no";
      type int32;
      description "slot no";
    }
    leaf card-flag {
      xr:xr-xml-map "fia_edm_defs:card_flag";
      type int32;
      description "card flag";
    }
    leaf evt-flag {
      xr:xr-xml-map "fia_edm_defs:evt_flag";
      type int32;
      description "evt flag";
    }
    leaf reg-flag {
      xr:xr-xml-map "fia_edm_defs:reg_flag";
      type int32;
      description "reg flag";
    }
    leaf instance {
      xr:xr-xml-map "fia_edm_defs:instance";
      type int32;
      description "instance";
    }
    leaf card-state {
      xr:xr-xml-map "fia_edm_defs:card_state";
      type uint8;
      description "card state";
    }
    leaf exp-num-asics {
      xr:xr-xml-map "fia_edm_defs:exp_num_asics";
      type uint32;
      description "exp num asics";
    }
    leaf exp-num-asics-per-fsdb {
      xr:xr-xml-map "fia_edm_defs:exp_num_asics_per_fsdb";
      type uint32;
      description "exp num asics per fsdb";
    }
    leaf is-powered {
      xr:xr-xml-map "fia_edm_defs:is_powered";
      type boolean;
      description "is powered";
    }
    leaf cxp-avail-bitmap {
      xr:xr-xml-map "fia_edm_defs:cxp_avail_bitmap";
      type uint64;
      description "cxp avail bitmap";
    }
    leaf num-ilkns-per-asic {
      xr:xr-xml-map "fia_edm_defs:num_ilkns_per_asic";
      type uint32;
      description "num ilkns per asic";
    }
    leaf num-local-ports-per-ilkn {
      xr:xr-xml-map "fia_edm_defs:num_local_ports_per_ilkn";
      type uint32;
      description "num local ports per ilkn";
    }
    leaf num-cos-per-port {
      xr:xr-xml-map "fia_edm_defs:num_cos_per_port";
      type uint8;
      description "num cos per port";
    }
  }

  grouping FIA-EDM-DEVICE {
    description "FIA EDM DEVICE";

    container asic-id {
      description "asic id";
      uses FIA-EDM-ASIC-IDENTITY;
    }
    leaf is-valid {
      xr:xr-xml-map "fia_edm_defs:is_valid";
      type boolean;
      description "is valid";
    }
    leaf fapid {
      xr:xr-xml-map "fia_edm_defs:fapid";
      type uint32;
      description "fapid";
    }
    leaf hotplug-event {
      xr:xr-xml-map "fia_edm_defs:hotplug_event";
      type uint32;
      description "hotplug event";
    }
    leaf slice-state {
      xr:xr-xml-map "fia_edm_defs:slice_state";
      type uint32;
      description "slice state";
    }
    leaf admin-state {
      xr:xr-xml-map "fia_edm_defs:admin_state";
      type uint8;
      description "admin state";
    }
    leaf oper-state {
      xr:xr-xml-map "fia_edm_defs:oper_state";
      type uint8;
      description "oper state";
    }
    leaf asic-state {
      xr:xr-xml-map "fia_edm_defs:asic_state";
      type uint8;
      description "asic state";
    }
    leaf last-init-cause {
      xr:xr-xml-map "fia_edm_defs:last_init_cause";
      type uint8;
      description "last init cause";
    }
    leaf num-pon-resets {
      xr:xr-xml-map "fia_edm_defs:num_pon_resets";
      type uint32;
      description "num pon resets";
    }
    leaf num-hard-resets {
      xr:xr-xml-map "fia_edm_defs:num_hard_resets";
      type uint32;
      description "num hard resets";
    }
    leaf last-pon-reset-timestamp {
      xr:xr-xml-map "fia_edm_defs:last_pon_reset_timestamp";
      type uint64;
      description "last pon reset timestamp";
    }
    leaf last-hard-reset-timestamp {
      xr:xr-xml-map "fia_edm_defs:last_hard_reset_timestamp";
      type uint64;
      description "last hard reset timestamp";
    }
    leaf local-switch-state {
      xr:xr-xml-map "fia_edm_defs:local_switch_state";
      type uint32;
      description "local switch state";
    }
  }

  grouping FIA-EDM-DRIVER-INFO {
    description "FIA EDM DRIVER INFO";
    leaf drv-version {
      xr:xr-xml-map "fia_edm_defs:drv_version";
      type uint32;
      description "drv version";
    }
    leaf coeff-major-rev {
      xr:xr-xml-map "fia_edm_defs:coeff_major_rev";
      type uint32;
      description "coeff major rev";
    }
    leaf coeff-minor-rev {
      xr:xr-xml-map "fia_edm_defs:coeff_minor_rev";
      type uint32;
      description "coeff minor rev";
    }
    leaf functional-role {
      xr:xr-xml-map "fia_edm_defs:functional_role";
      type uint8;
      description "functional role";
    }
    leaf issu-role {
      xr:xr-xml-map "fia_edm_defs:issu_role";
      type uint8;
      description "issu role";
    }
    leaf rack-name {
      xr:xr-xml-map "fia_edm_defs:rack_name";
      type string;
      description "rack name";
    }
    leaf rack-type {
      xr:xr-xml-map "fia_edm_defs:rack_type";
      type int32;
      description "rack type";
    }
    leaf rack-num {
      xr:xr-xml-map "fia_edm_defs:rack_num";
      type uint8;
      description "rack num";
    }
    leaf is-driver-ready {
      xr:xr-xml-map "fia_edm_defs:is_driver_ready";
      type boolean;
      description "is driver ready";
    }
    leaf card-avail-mask {
      xr:xr-xml-map "fia_edm_defs:card_avail_mask";
      type uint32;
      description "card avail mask";
    }
    leaf asic-avail-mask {
      xr:xr-xml-map "fia_edm_defs:asic_avail_mask";
      type uint64;
      description "asic avail mask";
    }
    leaf exp-asic-avail-mask {
      xr:xr-xml-map "fia_edm_defs:exp_asic_avail_mask";
      type uint64;
      description "exp asic avail mask";
    }
    leaf ucmc-ratio {
      xr:xr-xml-map "fia_edm_defs:ucmc_ratio";
      type uint32;
      description "ucmc ratio";
    }
    leaf asic-oper-notify-to-fsdb-pending-bmap {
      xr:xr-xml-map "fia_edm_defs:asic_oper_notify_to_fsdb_pending_"+
        "bmap";
      type uint64;
      description "asic oper notify to fsdb pending bmap";
    }
    leaf is-full-fgid-download-req {
      xr:xr-xml-map "fia_edm_defs:is_full_fgid_download_req";
      type boolean;
      description "is full fgid download req";
    }
    leaf is-fgid-download-in-progress {
      xr:xr-xml-map "fia_edm_defs:is_fgid_download_in_progress";
      type boolean;
      description "is fgid download in progress";
    }
    leaf is-fgid-download-completed {
      xr:xr-xml-map "fia_edm_defs:is_fgid_download_completed";
      type boolean;
      description "is fgid download completed";
    }
    leaf fsdb-conn-active {
      xr:xr-xml-map "fia_edm_defs:fsdb_conn_active";
      type boolean;
      description "fsdb conn active";
    }
    leaf fgid-conn-active {
      xr:xr-xml-map "fia_edm_defs:fgid_conn_active";
      type boolean;
      description "fgid conn active";
    }
    leaf issu-mgr-conn-active {
      xr:xr-xml-map "fia_edm_defs:issu_mgr_conn_active";
      type boolean;
      description "issu mgr conn active";
    }
    leaf fsdb-reg-active {
      xr:xr-xml-map "fia_edm_defs:fsdb_reg_active";
      type boolean;
      description "fsdb reg active";
    }
    leaf fgid-reg-active {
      xr:xr-xml-map "fia_edm_defs:fgid_reg_active";
      type boolean;
      description "fgid reg active";
    }
    leaf issu-mgr-reg-active {
      xr:xr-xml-map "fia_edm_defs:issu_mgr_reg_active";
      type boolean;
      description "issu mgr reg active";
    }
    leaf num-pm-conn-reqs {
      xr:xr-xml-map "fia_edm_defs:num_pm_conn_reqs";
      type uint8;
      description "num pm conn reqs";
    }
    leaf num-fsdb-conn-reqs {
      xr:xr-xml-map "fia_edm_defs:num_fsdb_conn_reqs";
      type uint8;
      description "num fsdb conn reqs";
    }
    leaf num-fgid-conn-reqs {
      xr:xr-xml-map "fia_edm_defs:num_fgid_conn_reqs";
      type uint8;
      description "num fgid conn reqs";
    }
    leaf num-fstats-conn-reqs {
      xr:xr-xml-map "fia_edm_defs:num_fstats_conn_reqs";
      type uint8;
      description "num fstats conn reqs";
    }
    leaf num-cm-conn-reqs {
      xr:xr-xml-map "fia_edm_defs:num_cm_conn_reqs";
      type uint8;
      description "num cm conn reqs";
    }
    leaf num-issu-mgr-conn-reqs {
      xr:xr-xml-map "fia_edm_defs:num_issu_mgr_conn_reqs";
      type uint8;
      description "num issu mgr conn reqs";
    }
    leaf num-peer-fia-conn-reqs {
      xr:xr-xml-map "fia_edm_defs:num_peer_fia_conn_reqs";
      type uint8;
      description "num peer fia conn reqs";
    }
    leaf is-gaspp-registered {
      xr:xr-xml-map "fia_edm_defs:is_gaspp_registered";
      type boolean;
      description "is gaspp registered";
    }
    leaf is-cih-registered {
      xr:xr-xml-map "fia_edm_defs:is_cih_registered";
      type boolean;
      description "is cih registered";
    }
    leaf offset-time-nsec {
      xr:xr-xml-map "fia_edm_defs:offset_time_nsec";
      type uint64;
      description "offset time nsec";
    }
    leaf drvr-startup-timestamp {
      xr:xr-xml-map "fia_edm_defs:drvr_startup_timestamp";
      type uint64;
      description "drvr startup timestamp";
    }
    leaf num-intf-ports {
      xr:xr-xml-map "fia_edm_defs:num_intf_ports";
      type uint32;
      description "num intf ports";
    }
    leaf uc-weight {
      xr:xr-xml-map "fia_edm_defs:uc_weight";
      type uint8;
      description "uc weight";
    }
    leaf respawn-count {
      xr:xr-xml-map "fia_edm_defs:respawn_count";
      type uint8;
      description "respawn count";
    }
    leaf total-asics {
      xr:xr-xml-map "fia_edm_defs:total_asics";
      type uint8;
      description "total asics";
    }
    leaf issu-ready-ntfy-pending {
      xr:xr-xml-map "fia_edm_defs:issu_ready_ntfy_pending";
      type boolean;
      description "issu ready ntfy pending";
    }
    leaf issu-abort-sent {
      xr:xr-xml-map "fia_edm_defs:issu_abort_sent";
      type boolean;
      description "issu abort sent";
    }
    leaf issu-abort-rcvd {
      xr:xr-xml-map "fia_edm_defs:issu_abort_rcvd";
      type boolean;
      description "issu abort rcvd";
    }
    leaf fc-mode {
      xr:xr-xml-map "fia_edm_defs:fc_mode";
      type uint8;
      description "fc mode";
    }
    leaf board-rev-id {
      xr:xr-xml-map "fia_edm_defs:board_rev_id";
      type uint32;
      description "board rev id";
    }

    list device-info {
      max-elements "40";
      description "device info";
      uses FIA-EDM-DEVICE;
    }

    list card-info {
      max-elements "16";
      description "card info";
      uses FIA-EDM-CARD-INFO;
    }
  }

  grouping FIA-EDM-STATE-CHANGE {
    description "FIA EDM STATE CHANGE";
    leaf admin-state {
      xr:xr-xml-map "fia_edm_defs:admin_state";
      type int8;
      description "admin state";
    }
    leaf oper-state {
      xr:xr-xml-map "fia_edm_defs:oper_state";
      type int8;
      description "oper state";
    }
    leaf error-state {
      xr:xr-xml-map "fia_edm_defs:error_state";
      type int8;
      description "error state";
    }
    leaf timestamp {
      xr:xr-xml-map "fia_edm_defs:timestamp";
      type uint64;
      description "timestamp";
    }
    leaf reasons {
      xr:xr-xml-map "fia_edm_defs:reasons";
      type string;
      description "reasons";
    }
  }

  grouping FIA-EDM-HISTORY {
    description "FIA EDM HISTORY";
    leaf histnum {
      xr:xr-xml-map "fia_edm_defs:histnum";
      type uint8;
      description "histnum";
    }
    leaf start-index {
      xr:xr-xml-map "fia_edm_defs:start_index";
      type uint8;
      description "start index";
    }

    list hist {
      max-elements "5";
      description "hist";
      uses FIA-EDM-STATE-CHANGE;
    }
  }

  grouping FIA-EDM-ASIC-IDENTITY {
    description "FIA EDM ASIC IDENTITY";
    leaf rack-type {
      xr:xr-xml-map "fia_edm_defs:rack_type";
      type uint32;
      description "rack type";
    }
    leaf asic-type {
      xr:xr-xml-map "fia_edm_defs:asic_type";
      type uint8;
      description "asic type";
    }
    leaf rack-num {
      xr:xr-xml-map "fia_edm_defs:rack_num";
      type uint32;
      description "rack num";
    }
    leaf slot-num {
      xr:xr-xml-map "fia_edm_defs:slot_num";
      type uint32;
      description "slot num";
    }
    leaf asic-instance {
      xr:xr-xml-map "fia_edm_defs:asic_instance";
      type uint32;
      description "asic instance";
    }
  }

  grouping FIA-EDM-LINK-IDENTITY {
    description "FIA EDM LINK IDENTITY";

    container asic-id {
      description "asic id";
      uses FIA-EDM-ASIC-IDENTITY;
    }
    leaf link-type {
      xr:xr-xml-map "fia_edm_defs:link_type";
      type uint8;
      description "link type";
    }
    leaf link-stage {
      xr:xr-xml-map "fia_edm_defs:link_stage";
      type uint8;
      description "link stage";
    }
    leaf link-num {
      xr:xr-xml-map "fia_edm_defs:link_num";
      type uint32;
      description "link num";
    }
    leaf phy-link-num {
      xr:xr-xml-map "fia_edm_defs:phy_link_num";
      type uint32;
      description "phy link num";
    }
  }

  grouping FIA-EDM-RXLINK {
    description "FIA EDM RXLINK";

    container this-link {
      description "this link";
      uses FIA-EDM-LINK-IDENTITY;
    }

    container far-end-link {
      description "far end link";
      uses FIA-EDM-LINK-IDENTITY;
    }

    container far-end-link-in-hw {
      description "far end link in hw";
      uses FIA-EDM-LINK-IDENTITY;
    }

    container history {
      description "history";
      uses FIA-EDM-HISTORY;
    }
    leaf speed {
      xr:xr-xml-map "fia_edm_defs:speed";
      type uint32;
      description "speed";
    }
    leaf stage {
      xr:xr-xml-map "fia_edm_defs:stage";
      type uint8;
      description "stage";
    }
    leaf is-link-valid {
      xr:xr-xml-map "fia_edm_defs:is_link_valid";
      type boolean;
      description "is link valid";
    }
    leaf is-conf-pending {
      xr:xr-xml-map "fia_edm_defs:is_conf_pending";
      type boolean;
      description "is conf pending";
    }
    leaf admin-state {
      xr:xr-xml-map "fia_edm_defs:admin_state";
      type uint8;
      description "admin state";
    }
    leaf oper-state {
      xr:xr-xml-map "fia_edm_defs:oper_state";
      type uint8;
      description "oper state";
    }
    leaf error-state {
      xr:xr-xml-map "fia_edm_defs:error_state";
      type uint8;
      description "error state";
    }
    leaf flags {
      xr:xr-xml-map "fia_edm_defs:flags";
      type string;
      description "flags";
    }
    leaf flap-cnt {
      xr:xr-xml-map "fia_edm_defs:flap_cnt";
      type uint32;
      description "flap cnt";
    }
    leaf num-admin-shuts {
      xr:xr-xml-map "fia_edm_defs:num_admin_shuts";
      type uint32;
      description "num admin shuts";
    }
  }
}
