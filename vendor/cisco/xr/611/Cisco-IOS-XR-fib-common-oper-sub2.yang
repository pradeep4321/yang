submodule Cisco-IOS-XR-fib-common-oper-sub2 {

  belongs-to Cisco-IOS-XR-fib-common-oper {
    prefix Cisco-IOS-XR-fib-common-oper;
  }

  /*** LINKAGE (IMPORTS / INCLUDES) ***/

  import ietf-inet-types { prefix "inet"; }

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR fib-common package operational data.

     Copyright (c) 2013-2016 by Cisco Systems, Inc.
     All rights reserved.";

  revision "2015-11-09" {
    description
      "IOS XR 6.0 revision.";
  }

  typedef Fib-rpf-mode {
    type enumeration {
      enum fib-rpf-mode-strict {
        description "RPF mode strict";
      }
      enum fib-rpf-mode-loose {
        description "RPF mode loose";
      }
      enum fib-rpf-mode-unknown {
        description "RPF mode unknown";
      }
    }
    description "RPF mode types";
  }
  typedef Fibidb-oper {
    type enumeration {
      enum fibidb-none {
        value 0;
        description "fibidb none";
      }
      enum fibidb-create {
        value 1;
        description "fibidb create";
      }
      enum fibidb-delete {
        value 2;
        description "fibidb delete";
      }
      enum fibidb-modify {
        value 3;
        description "fibidb modify";
      }
      enum fibidb-max {
        value 4;
        description "fibidb max";
      }
    }
    description "Fibidb oper";
  }
  typedef Ss-lba-state {
    type enumeration {
      enum l3 {
        description "L3 Load Balance config";
      }
      enum l4 {
        description "L4 Load Balance config";
      }
    }
    description "Load Balance config";
  }
  typedef Fib-sh-ipencap-hdr {
    type enumeration {
      enum fib-sh-ip-encap-none {
        description "No Header";
      }
      enum fib-sh-ip-encap-ip4 {
        description "IPv4 Header";
      }
      enum fib-sh-ip-encap-ip6 {
        description "IPv6 Header";
      }
      enum fib-sh-ip-encap-udp {
        description "UDP Header";
      }
      enum fib-sh-ip-encap-lisp {
        description "Lisp Header";
      }
    }
    description "IP Encap Header Type";
  }
  typedef Fib-neh-special {
    type enumeration {
      enum nh-not-found {
        description "nh not found";
      }
      enum nh-null0 {
        description "nh null0";
      }
      enum nh-punt {
        description "nh punt";
      }
      enum nh-drop {
        description "nh drop";
      }
      enum nh-glean {
        description "nh glean";
      }
      enum nh-receive {
        description "nh receive";
      }
      enum nh-broadcast {
        description "nh broadcast";
      }
      enum nh-external {
        description "nh external";
      }
      enum nh-lisp {
        description "nh lisp";
      }
      enum nh-lookup {
        description "nh lookup";
      }
      enum nh-max-type {
        description "nh max type";
      }
    }
    description "Fib neh special";
  }
  typedef Fib-neh {
    type enumeration {
      enum nh-local {
        description "nh local";
      }
      enum nh-remote {
        description "nh remote";
      }
      enum nh-special {
        description "nh special";
      }
    }
    description "Fib neh";
  }
  typedef Fib-adjacency-show {
    type enumeration {
      enum fib-adjacency-normal {
        description "Normal adjacency";
      }
      enum fib-adjacency-null {
        description "Null adjacency";
      }
      enum fib-adjacency-punt {
        description "Punt adjacency";
      }
      enum fib-adjacency-drop {
        description "Drop adjacency";
      }
      enum fib-adjacency-glean {
        description "Glean adjacency";
      }
      enum fib-adjacency-discard {
        description "Discard adjacency";
      }
      enum fib-adjacency-broadcast {
        description "Broadcast adjacency";
      }
      enum fib-adjacency-external {
        description "external adjacency";
      }
      enum fib-adjacency-lisp {
        description "LISP adjacency";
      }
      enum fib-adjacency-unknown {
        description "Unknown adjacency";
      }
    }
    description "Adjacency types";
  }
  typedef Fib-loadshare-show {
    type enumeration {
      enum fib-load-share-none {
        description "No loadsharing";
      }
      enum fib-load-share-per-packet {
        description "Per packet loadsharing";
      }
      enum fib-load-share-dest-sharing {
        description "Destination loadsharing";
      }
    }
    description "Loadsharing type";
  }
  typedef Fib-frr-protocol-show {
    type enumeration {
      enum frr-protocol-ipv4 {
        description "frr protocol ipv4";
      }
      enum frr-protocol-ipv6 {
        description "frr protocol ipv6";
      }
      enum frr-protocol-mpls {
        description "frr protocol mpls";
      }
    }
    description "Fib frr protocol show";
  }

  grouping FIB-MPLS-RPF-IF-MAP {
    description "Mapping between interface and neighbour";
    leaf rpf-path-index {
      xr:xr-xml-map "fib:rpf_path_index";
      type uint32;
      description "rpf path index";
    }
    leaf rpf-ifh {
      xr:xr-xml-map "fib:rpf_ifh";
      type uint32;
      description "rpf ifh";
    }
  }

  grouping FIB-MPLS-RPF-V6-NBR {
    description "RPF info for V4 neighbour";
    leaf rpf-tbl-id {
      xr:xr-xml-map "fib:rpf_tbl_id";
      type uint32;
      description "rpf tbl id";
    }
    leaf rpf-v6-addr {
      xr:xr-xml-map "fib:rpf_v6_addr";
      type inet:ipv6-address;
      description "rpf v6 addr";
    }
  }

  grouping FIB-MPLS-RPF-V4-NBR {
    description "RPF info for V4 neighbour";
    leaf rpf-tbl-id {
      xr:xr-xml-map "fib:rpf_tbl_id";
      type uint32;
      description "rpf tbl id";
    }
    leaf rpf-v4-addr {
      xr:xr-xml-map "fib:rpf_v4_addr";
      type inet:ipv4-address;
      description "rpf v4 addr";
    }
  }

  grouping FIB-MPLS-LEAF-RPF {
    description " Leaf RPF info";
    leaf rpf-flags {
      xr:xr-xml-map "fib:rpf_flags";
      type uint32;
      description "RPF flags";
    }
    leaf rpf-pl-flags {
      xr:xr-xml-map "fib:rpf_pl_flags";
      type uint32;
      description "RPF pathlist flags";
    }
    leaf rpf-create-ts {
      xr:xr-xml-map "fib:rpf_create_ts";
      type uint64;
      description "Time when the LRPF was created";
    }
    leaf rpf-mod-ts {
      xr:xr-xml-map "fib:rpf_mod_ts";
      type uint64;
      description "Last time the LRPF modified";
    }
    leaf rpf-pd-ts {
      xr:xr-xml-map "fib:rpf_pd_ts";
      type uint64;
      description "Last time the PD action was sent for the LRPF";
    }
    leaf rpf-hardware {
      xr:xr-xml-map "fib:rpf_hardware";
      type yang:hex-string;
      description "Platform Hardware info";
    }
    leaf-list rpf-if {
      xr:xr-xml-map "fib:rpf_if_list";
      type xr:Interface-name;
      description "Array of interfaces in interface list";
    }

    list rpf-v4-nbr {
      description "Array of V4 neighbours";
      uses FIB-MPLS-RPF-V4-NBR;
    }

    list rpf-v6-nbr {
      description "Array of V6 neighbours";
      uses FIB-MPLS-RPF-V6-NBR;
    }

    list rpf-if-map {
      description "Array of nbr/interface mapping";
      uses FIB-MPLS-RPF-IF-MAP;
    }
  }

  grouping FIB-MPLS-LLC {
    description "FIB MPLS LLC";
    leaf local-label {
      xr:xr-xml-map "fib:local_label";
      type uint32;
      description "local label";
    }
    leaf source-xr {
      xr:xr-xml-map "fib:source-xr";
      type uint32;
      description "source xr";
    }
    leaf type {
      xr:xr-xml-map "fib:type";
      type uint8;
      description "type";
    }
    leaf pfx {
      xr:xr-xml-map "fib:pfx";
      type string {
        length "0..52";
      }
      description "pfx";
    }
    leaf pfx-tblid {
      xr:xr-xml-map "fib:pfx_tblid";
      type uint32;
      description "pfx tblid";
    }
    leaf update-ts {
      xr:xr-xml-map "fib:update_ts";
      type uint64;
      description "update ts";
    }
    leaf retry-ts {
      xr:xr-xml-map "fib:retry_ts";
      type uint64;
      description "retry ts";
    }
    leaf num-retries {
      xr:xr-xml-map "fib:num_retries";
      type uint32;
      description "num retries";
    }
  }

  grouping FIB-SH-PLAT-CAPABILITIES {
    description "FIB platform capabilities";
    leaf fpc-num-l3-lbl-levels {
      xr:xr-xml-map "fib:fpc_num_l3_lbl_levels";
      type uint8;
      description "L3 LBL levels";
    }
    leaf fpc-num-l3-lbl-paths {
      xr:xr-xml-map "fib:fpc_num_l3_lbl_paths";
      type uint8;
      description "L3 Hash buckets";
    }
    leaf fpc-num-l3-lbl-rec-paths {
      xr:xr-xml-map "fib:fpc_num_l3_lbl_rec_paths";
      type uint8;
      description "L3 Recursive Hash buckets";
    }
    leaf fpc-num-l3-ucmp-paths {
      xr:xr-xml-map "fib:fpc_num_l3_ucmp_paths";
      type uint8;
      description "L3 Unequal cost hash buckets";
    }
    leaf fpc-num-fwding-stages {
      xr:xr-xml-map "fib:fpc_num_fwding_stages";
      type uint8;
      description "Forwarding stages";
    }
    leaf fpc-local-label-split {
      xr:xr-xml-map "fib:fpc_local_label_split";
      type uint32;
      description "Label split";
    }
    leaf fpc-stats-support {
      xr:xr-xml-map "fib:fpc_stats_support";
      type boolean;
      description "Statistics support";
    }
    leaf fpc-platf-ready-cb-wait {
      xr:xr-xml-map "fib:fpc_platf_ready_cb_wait";
      type boolean;
      description "Plat ready cb register";
    }
    leaf fpc-num-paths-per-pbts-class {
      xr:xr-xml-map "fib:fpc_num_paths_per_pbts_class";
      type uint8;
      description "Path per tunnel class";
    }
    leaf fpc-platf-v4-upd-disable {
      xr:xr-xml-map "fib:fpc_platf_v4_upd_disable";
      type boolean;
      description "V4 update disable";
    }
    leaf fpc-platf-v6-upd-disable {
      xr:xr-xml-map "fib:fpc_platf_v6_upd_disable";
      type boolean;
      description "V6 update disable";
    }
    leaf fpc-lba-tuples-default {
      xr:xr-xml-map "fib:fpc_lba_tuples_default";
      type uint32;
      description "LBA tuples";
    }
    leaf fpc-mraps-support {
      xr:xr-xml-map "fib:fpc_mraps_support";
      type boolean;
      description "MRAPS support";
    }
    leaf fpc-pbts-defclass-support {
      xr:xr-xml-map "fib:fpc_pbts_defclass_support";
      type boolean;
      description "PBTS default class support";
    }
    leaf fpc-loadinfo-filter-support {
      xr:xr-xml-map "fib:fpc_loadinfo_filter_support";
      type boolean;
      description "loadinfo filter support";
    }
    leaf fpc-nhid {
      xr:xr-xml-map "fib:fpc_nhid";
      type boolean;
      description "NHID support";
    }
    leaf fpc-platf-temp-back-walk-reqd {
      xr:xr-xml-map "fib:fpc_platf_temp_back_walk_reqd";
      type boolean;
      description "Backwalk dependents is required";
    }
    leaf fpc-link-mpls-nhinfo-in-ipv6-thread-support {
      xr:xr-xml-map "fib:fpc_link_mpls_nhinfo_in_ipv6_thread_suppor"+
        "t";
      type boolean;
      description "Link MPLS IPv6 NH support";
    }
    leaf fpc-exclude-deag-bkup {
      xr:xr-xml-map "fib:fpc_exclude_deag_bkup";
      type boolean;
      description "Exclude Deag backup Paths";
    }
    leaf fpc-dlb-support {
      xr:xr-xml-map "fib:fpc_dlb_support";
      type boolean;
      description "Per-destination load-balancing support";
    }
    leaf fpc-prefix-filter-support {
      xr:xr-xml-map "fib:fpc_prefix_filter_support";
      type uint8;
      description "Prefix filter level of support";
    }
    leaf fpc-slowpath-ingress-inject-reqd {
      xr:xr-xml-map "fib:fpc_slowpath_ingress_inject_reqd";
      type boolean;
      description "Slowpath ingress inject required";
    }

    list fpc-lisp-decap-over-v4 {
      min-elements "3";
      max-elements "3";
      description "LISP Decap over 4";
      leaf entry {
        type boolean;
        description "Array entry.";
      }
    }

    list fpc-lisp-decap-over-v6 {
      min-elements "3";
      max-elements "3";
      description "LISP Decap over 6";
      leaf entry {
        type boolean;
        description "Array entry.";
      }
    }

    list fpc-lisp-ucmp {
      min-elements "3";
      max-elements "3";
      description "LISP UCMP support";
      leaf entry {
        type boolean;
        description "Array entry.";
      }
    }

    list fpc-resolve-via-table {
      min-elements "3";
      max-elements "3";
      description "Fallback VRF support";
      leaf entry {
        type boolean;
        description "Array entry.";
      }
    }
  }

  grouping FIB-SH-PROTO-FRR-STATS {
    description "FIB per protocol frr counters";
    leaf mi-num-intf-frr {
      xr:xr-xml-map "fib:mi_num_intf_frr";
      type uint32;
      description "number of FRR events sent on nh interface down";
    }
    leaf mi-num-parent-intf-frr {
      xr:xr-xml-map "fib:mi_num_parent_intf_frr";
      type uint32;
      description
        "number of FRR events sent on nh parent interface
        down";
    }
    leaf mi-num-pfi-intf-down {
      xr:xr-xml-map "fib:mi_num_pfi_intf_down";
      type uint32;
      description "number of interface down FRR events from PFI";
    }
    leaf mi-num-bfd-down {
      xr:xr-xml-map "fib:mi_num_bfd_down";
      type uint32;
      description "number of NH down FRR events frm BFD";
    }
    leaf mi-num-prot-frr-objects {
      xr:xr-xml-map "fib:mi_num_prot_frr_objects";
      type uint32;
      description "total number of prot FRR objects";
    }
    leaf mi-num-bkup-frr-objects {
      xr:xr-xml-map "fib:mi_num_bkup_frr_objects";
      type uint32;
      description "total number of backup FRR objects";
    }
    leaf mi-num-tunid-allocs {
      xr:xr-xml-map "fib:mi_num_tunid_allocs";
      type uint32;
      description
        "total number of successful FRR tunnel ID
        allocations";
    }
    leaf mi-num-tunid-alloc-failures {
      xr:xr-xml-map "fib:mi_num_tunid_alloc_failures";
      type uint32;
      description
        "total number of FRR tunnel ID allocation
        failures";
    }
    leaf mi-num-tunid-frees {
      xr:xr-xml-map "fib:mi_num_tunid_frees";
      type uint32;
      description "total number of successful FRR tunnel ID frees";
    }
    leaf mi-num-tunid-free-failures {
      xr:xr-xml-map "fib:mi_num_tunid_free_failures";
      type uint32;
      description "total number of FRR tunnel ID free failures";
    }
    leaf mi-num-frr-reset-queue-adds {
      xr:xr-xml-map "fib:mi_num_frr_reset_queue_adds";
      type uint32;
      description "number of frr reset queue adds";
    }
    leaf mi-num-frr-reset-queue-remove {
      xr:xr-xml-map "fib:mi_num_frr_reset_queue_remove";
      type uint32;
      description "number of frr reset queue deletes";
    }
    leaf mi-num-frr-reset {
      xr:xr-xml-map "fib:mi_num_frr_reset";
      type uint32;
      description "number of frr resets";
    }
    leaf mi-num-frr-proto-events {
      xr:xr-xml-map "fib:mi_num_frr_proto_events";
      type uint32;
      description "number of frr events received in proto thread";
    }
    leaf mi-num-frr-logs {
      xr:xr-xml-map "fib:mi_num_frr_logs";
      type uint32;
      description "frr log size";
    }
  }

  grouping FIB-SH-ROUTE-DEL-TS {
    description "FIB SH ROUTE DEL TS";
    leaf tableid {
      xr:xr-xml-map "fib:tableid";
      type uint32;
      description "tableid";
    }
    leaf prfx {
      xr:xr-xml-map "fib:prfx";
      type string {
        length "0..16";
      }
      description "prfx";
    }
    leaf prfx-len {
      xr:xr-xml-map "fib:prfx_len";
      type uint16;
      description "prfx len";
    }
    leaf prfx-proto {
      xr:xr-xml-map "fib:prfx_proto";
      type uint16;
      description "prfx proto";
    }
    leaf msec-time {
      xr:xr-xml-map "fib:msec_time";
      type uint64;
      description "msec time";
    }
  }

  grouping FIB-SH-PROTO-PURGE-STATS {
    description "FIB per protocol purge counters";
    leaf-list fpp-cntr {
      xr:xr-xml-map "fib:fpp_cntrs";
      type uint32;
      max-elements "3";
      description "the number of frees for this proto";
    }
  }

  grouping FIB-SH-GTRIE-FN-TIMING {
    description
      "FIB timing statistics for individual gtrie
      functions";
    leaf fgft-fn {
      xr:xr-xml-map "fib:fgft_fn";
      type string {
        length "0..64";
      }
      description "Gtrie operation";
    }
    leaf fgft-tot-updates {
      xr:xr-xml-map "fib:fgft_tot_updates";
      type uint64;
      description "Total number of updates";
    }
    leaf fgft-tot-updates-zero {
      xr:xr-xml-map "fib:fgft_tot_updates_zero";
      type uint64;
      description
        "Total number of updates with zero timing (due to
        timestamp granularity)";
    }
    leaf fgft-tot-upd-time {
      xr:xr-xml-map "fib:fgft_tot_upd_time";
      type uint64;
      description "Total time for updates";
    }
    leaf fgft-max-time {
      xr:xr-xml-map "fib:fgft_max_time";
      type uint64;
      description "Time for the update";
    }
    leaf fgft-max-tstamp {
      xr:xr-xml-map "fib:fgft_max_tstamp";
      type uint64;
      description "Time stamp of max update";
    }
  }

  grouping FIB-SH-GTRIE-TIMING {
    description "FIB platform update statistics";
    leaf fgt-num-success {
      xr:xr-xml-map "fib:fgt_num_success";
      type uint64;
      description "Number of successful updates";
    }
    leaf fgt-num-failure {
      xr:xr-xml-map "fib:fgt_num_failure";
      type uint64;
      description "Number of unsuccessful updates";
    }
    leaf fgt-upd-total-time {
      xr:xr-xml-map "fib:fgt_upd_total_time";
      type uint64;
      description "Total time for all pd updates";
    }

    list fgt-gtrie-fn-timing {
      description
        "Array of max time info indexed by gtrie function";
      uses FIB-SH-GTRIE-FN-TIMING;
    }
  }

  grouping FIB-SH-OBJ-STATS {
    description "FIB Max time statistics for each FIB object";
    leaf fos-tot-updates {
      xr:xr-xml-map "fib:fos_tot_updates";
      type uint64;
      description "Total number of updates";
    }
    leaf fos-tot-updates-zero {
      xr:xr-xml-map "fib:fos_tot_updates_zero";
      type uint64;
      description
        "Total number of updates with zero timing (due to
        timestamp granularity)";
    }
    leaf fos-tot-upd-time {
      xr:xr-xml-map "fib:fos_tot_upd_time";
      type uint64;
      description "Total time for updates";
    }
    leaf fos-max-action-type {
      xr:xr-xml-map "fib:fos_max_action_type";
      type uint32;
      description "The action that took max time";
    }
    leaf fos-max-time {
      xr:xr-xml-map "fib:fos_max_time";
      type uint64;
      description "Time for the update";
    }
    leaf fos-max-tstamp {
      xr:xr-xml-map "fib:fos_max_tstamp";
      type uint64;
      description "Time stamp of max update";
    }
  }

  grouping FIB-SH-PLATF-UPD-STATS {
    description "FIB platform update statistics";
    leaf fpus-num-success {
      xr:xr-xml-map "fib:fpus_num_success";
      type uint64;
      description "Number of successful updates";
    }
    leaf fpus-num-failure {
      xr:xr-xml-map "fib:fpus_num_failure";
      type uint64;
      description "Number of unsuccessful updates";
    }
    leaf fpus-upd-total-time {
      xr:xr-xml-map "fib:fpus_upd_total_time";
      type uint64;
      description "Total time for all pd updates";
    }

    list fpus-obj-stat {
      description "Array of max time info indexed by object type";
      uses FIB-SH-OBJ-STATS;
    }
  }

  grouping FIB-SH-PROTO-DEBUG-STATS {
    description "FIB per protocol debug information";

    container fpd-platf-upd-stats {
      description "platform update statistics";
      uses FIB-SH-PLATF-UPD-STATS;
    }

    container fpd-gtrie-timing {
      description "Gtrie timing statistics";
      uses FIB-SH-GTRIE-TIMING;
    }
    leaf fpd-gbltbl-entries {
      xr:xr-xml-map "fib:fpd_gbltbl_entries";
      type uint64;
      description "the number of fib entries in global tbl";
    }
    leaf fpd-gbltbl-rej-entries {
      xr:xr-xml-map "fib:fpd_gbltbl_rej_entries";
      type uint64;
      description "the number of fib entries in global retry tbl";
    }
    leaf fpd-vrftbl-entries {
      xr:xr-xml-map "fib:fpd_vrftbl_entries";
      type uint64;
      description "the number of fib entries in vrf tbls";
    }
    leaf fpd-vrftbl-rej-entries {
      xr:xr-xml-map "fib:fpd_vrftbl_rej_entries";
      type uint64;
      description "the number of fib entries in vrf retry tbls";
    }
    leaf fpd-num-tbls {
      xr:xr-xml-map "fib:fpd_num_tbls";
      type uint32;
      description "the number of tables in table set";
    }
    leaf fpd-bcdl-msgs {
      xr:xr-xml-map "fib:fpd_bcdl_msgs";
      type uint64;
      description "the number of bcdl msgs";
    }
    leaf fpd-route-upd {
      xr:xr-xml-map "fib:fpd_route_upd";
      type uint64;
      description "the number of route updates";
    }
    leaf fpd-route-del {
      xr:xr-xml-map "fib:fpd_route_del";
      type uint64;
      description "the number of route deletes";
    }
    leaf fpd-route-rcv {
      xr:xr-xml-map "fib:fpd_route_rcv";
      type uint64;
      description "the number of routes received";
    }
    leaf fpd-route-drops {
      xr:xr-xml-map "fib:fpd_route_drops";
      type uint64;
      description "the number of routes dropped";
    }
    leaf fpd-lbl-recycled {
      xr:xr-xml-map "fib:fpd_lbl_recycled";
      type uint64;
      description
        "the number of routes handled with recycled label";
    }
    leaf fpd-version-mismatch-drops {
      xr:xr-xml-map "fib:fpd_version_mismatch_drops";
      type uint64;
      description
        "the number of routes dropped because of version
        mismatch";
    }
    leaf fpd-adj-upd {
      xr:xr-xml-map "fib:fpd_adj_upd";
      type uint64;
      description "the number of adjacency updates";
    }
    leaf fpd-adj-del {
      xr:xr-xml-map "fib:fpd_adj_del";
      type uint64;
      description "the number of adjacency deletes";
    }
    leaf fpd-adj-upd-tx {
      xr:xr-xml-map "fib:fpd_adj_upd_tx";
      type uint64;
      description "number of TX adjacency updates from AIB";
    }
    leaf fpd-adj-upd-tx-nh-found {
      xr:xr-xml-map "fib:fpd_adj_upd_tx_nh_found";
      type uint64;
      description
        "number of TX adjacency updates that found or
        created NH";
    }
    leaf fpd-adj-upd-tx-retry-created {
      xr:xr-xml-map "fib:fpd_adj_upd_tx_retry_created";
      type uint64;
      description
        "number of TX adjacency updates that went to
        retry";
    }
    leaf fpd-adj-tx-retry-nh-found {
      xr:xr-xml-map "fib:fpd_adj_tx_retry_nh_found";
      type uint64;
      description
        "number of TX adj retries that found or created
        NH";
    }
    leaf fpd-adj-tx-retry-obj-reinit {
      xr:xr-xml-map "fib:fpd_adj_tx_retry_obj_reinit";
      type uint64;
      description "number of times TX NH retry objects updated";
    }
    leaf fpd-adj-drops {
      xr:xr-xml-map "fib:fpd_adj_drops";
      type uint64;
      description " number of adj updates dropped because of OOR";
    }
    leaf fpd-adj-msg {
      xr:xr-xml-map "fib:fpd_adj_msg";
      type uint64;
      description "number of AIB messages";
    }
    leaf fpd-te-rcv {
      xr:xr-xml-map "fib:fpd_te_rcv";
      type uint64;
      description "the number of TE upds received";
    }
    leaf fpd-te-version-mismatch-drops {
      xr:xr-xml-map "fib:fpd_te_version_mismatch_drops";
      type uint64;
      description
        "the number of TE upds dropped because of version
        mismatch";
    }
    leaf fpd-num-retry-touts {
      xr:xr-xml-map "fib:fpd_num_retry_touts";
      type uint64;
      description "the number of retry timeouts";
    }
    leaf fpd-ldi-num-fixedup {
      xr:xr-xml-map "fib:fpd_ldi_num_fixedup";
      type uint64;
      description "the number of fixup LDIs";
    }
    leaf fpd-ldi-num-correct-fixup {
      xr:xr-xml-map "fib:fpd_ldi_num_correct_fixup";
      type uint64;
      description "the number of corrected fixup LDIs";
    }
    leaf fpd-pl-num-queued-fixedup {
      xr:xr-xml-map "fib:fpd_pl_num_queued_fixedup";
      type uint64;
      description "the number of PL queued for fixup";
    }
    leaf fpd-pl-num-correct-fixup {
      xr:xr-xml-map "fib:fpd_pl_num_correct_fixup";
      type uint64;
      description "the number of corrected fixup PLs";
    }
    leaf fpd-pl-retry-add-exist {
      xr:xr-xml-map "fib:fpd_pl_retry_add_exist";
      type uint64;
      description
        "the number PLs added to retry while already in
        retry";
    }
    leaf fpd-pl-inline-res-q {
      xr:xr-xml-map "fib:fpd_pl_inline_res_q";
      type uint64;
      description
        "the number of PLs linked to resolving tables for
        inline res";
    }
    leaf fpd-pl-with-backup-create-count {
      xr:xr-xml-map "fib:fpd_pl_with_backup_create_count";
      type uint64;
      description "number of pl creates with backu path";
    }
    leaf fpd-pl-with-backup-del-count {
      xr:xr-xml-map "fib:fpd_pl_with_backup_del_count";
      type uint64;
      description "number of pl deletes with backup path";
    }
    leaf fpd-pl-backup-enable-count {
      xr:xr-xml-map "fib:fpd_pl_backup_enable_count";
      type uint64;
      description "number of PLs marked to include backup path";
    }
    leaf fpd-pl-backup-disable-count {
      xr:xr-xml-map "fib:fpd_pl_backup_disable_count";
      type uint64;
      description " number of PLs unmarked to include backup path";
    }
    leaf fpd-pl-fast-nfn-count {
      xr:xr-xml-map "fib:fpd_pl_fast_nfn_count";
      type uint64;
      description "number of PLs visited on fast notification";
    }
    leaf fpd-ldi-backup-activate-count {
      xr:xr-xml-map "fib:fpd_ldi_backup_activate_count";
      type uint64;
      description "number of ldi backup path activications";
    }
    leaf fpd-ldi-last-backup-activate-time {
      xr:xr-xml-map "fib:fpd_ldi_last_backup_activate_time";
      type uint64;
      description "ldi mod time for last backup activation";
    }
    leaf fpd-ldi-max-backup-activate-time {
      xr:xr-xml-map "fib:fpd_ldi_max_backup_activate_time";
      type uint64;
      description "max ldi mod time for backup activation";
    }
    leaf fpd-ldi-min-backup-activate-time {
      xr:xr-xml-map "fib:fpd_ldi_min_backup_activate_time";
      type uint64;
      description "min ldi mod time for backup activation";
    }
    leaf fpd-ldi-total-backup-activate-time {
      xr:xr-xml-map "fib:fpd_ldi_total_backup_activate_time";
      type uint64;
      description "total ldi mod time for backup activation";
    }
    leaf fpd-ldi-avg-backup-activate-time {
      xr:xr-xml-map "fib:fpd_ldi_avg_backup_activate_time";
      type uint64;
      description "avg ldi mod time for backup activation";
    }
    leaf fpd-recursion-constraint-count {
      xr:xr-xml-map "fib:fpd_recursion_constraint_count";
      type uint64;
      description
        "number of resolution failures because of
        recursion constraint";
    }
    leaf fpd-ldi-num-del-refcnt {
      xr:xr-xml-map "fib:fpd_ldi_num_del_refcnt";
      type uint64;
      description "the number of deleted with non-zero refcount";
    }
    leaf fpd-retryq-size {
      xr:xr-xml-map "fib:fpd_retryq_size";
      type uint32;
      description "the number of elements in retryq";
    }
    leaf fpd-num-allocs {
      xr:xr-xml-map "fib:fpd_num_allocs";
      type uint64;
      description "the number of allocs for this proto";
    }
    leaf fpd-num-frees {
      xr:xr-xml-map "fib:fpd_num_frees";
      type uint64;
      description "the number of frees for this proto";
    }
    leaf-list fpd-gbltbl-src-entry {
      xr:xr-xml-map "fib:fpd_gbltbl_src_entries";
      type uint64;
      max-elements "14";
      description
        "Number of global routes from                    
        each route source";
    }
    leaf-list fpd-vrftbl-src-entry {
      xr:xr-xml-map "fib:fpd_vrftbl_src_entries";
      type uint64;
      max-elements "14";
      description
        "Number of vrf routes from                       
        each route source";
    }
    leaf-list fpd-num-retry {
      xr:xr-xml-map "fib:fpd_num_retries";
      type uint64;
      description "the number of retries of each type";
    }
  }

  grouping FIB-SH-MISC {
    description "FIB miscellaneous info";

    container mi-issu-state {
      description "FIB ISSU state";
      uses FIB-ISSU-STATE;
    }

    container mi-plat-capabilities {
      description "FIB platform capabilities";
      uses FIB-SH-PLAT-CAPABILITIES;
    }
    leaf mi-pfi-ifh-upd {
      xr:xr-xml-map "fib:mi_pfi_ifh_upd";
      type uint64;
      description "number of pfi ifh create notif";
    }
    leaf mi-pfi-ifh-del {
      xr:xr-xml-map "fib:mi_pfi_ifh_del";
      type uint64;
      description "number of pfi ifh delete notif";
    }
    leaf mi-pfi-ifh-stale {
      xr:xr-xml-map "fib:mi_pfi_ifh_stale";
      type uint64;
      description "number of stale ifh removed";
    }
    leaf mi-tot-plat-upd-time {
      xr:xr-xml-map "fib:mi_tot_plat_upd_time";
      type uint64;
      description "total platform update time";
    }
    leaf mi-tot-gtrie-time {
      xr:xr-xml-map "fib:mi_tot_gtrie_time";
      type uint64;
      description "total time spent in gtrie operations";
    }
    leaf mi-tot-dnld-time {
      xr:xr-xml-map "fib:mi_tot_dnld_time";
      type uint64;
      description "total download time";
    }
    leaf mi-clock-time {
      xr:xr-xml-map "fib:mi_clock_time";
      type uint64;
      description "clock download time";
    }
    leaf mi-cpu-time {
      xr:xr-xml-map "fib:mi_cpu_time";
      type uint64;
      description "CPU download time";
    }
    leaf mi-shm-reset-ts {
      xr:xr-xml-map "fib:mi_shm_reset_ts";
      type uint64;
      description "Last FIB shared memory reset time stamp";
    }
    leaf mi-idb-recycle-count {
      xr:xr-xml-map "fib:mi_idb_recycle_count";
      type uint32;
      description "Number of idbs that hit ifh recycle";
    }
    leaf mi-idb-recycle-cleanup-count {
      xr:xr-xml-map "fib:mi_idb_recycle_cleanup_count";
      type uint32;
      description
        "Number of idb cleaned up after hitting ifh
        recycle";
    }
    leaf mi-num-mgmt-list {
      xr:xr-xml-map "fib:mi_num_mgmt_list";
      type uint32;
      description "Number of management interfaces";
    }
    leaf mi-num-virtual-ll-addresses-added {
      xr:xr-xml-map "fib:mi_num_virtual_ll_addresses_added";
      type uint32;
      description "mi num virtual ll addresses added";
    }
    leaf mi-num-virtual-ll-addresses-deleted {
      xr:xr-xml-map "fib:mi_num_virtual_ll_addresses_deleted";
      type uint32;
      description "mi num virtual ll addresses deleted";
    }
    leaf mi-num-virtual-ll-addresses-dropped {
      xr:xr-xml-map "fib:mi_num_virtual_ll_addresses_dropped";
      type uint32;
      description "mi num virtual ll addresses dropped";
    }
    leaf mi-num-virtual-ll-addresses-cached {
      xr:xr-xml-map "fib:mi_num_virtual_ll_addresses_cached";
      type uint32;
      description "mi num virtual ll addresses cached";
    }
    leaf mi-cpuless-init {
      xr:xr-xml-map "fib:mi_cpuless_init";
      type boolean;
      description "cpuless node list init";
    }
    leaf mi-cpuless-count {
      xr:xr-xml-map "fib:mi_cpuless_count";
      type uint32;
      description "count of cpuless line cards";
    }
    leaf mi-prefer-aib-routes-over-rib-oper {
      xr:xr-xml-map "fib:mi_prefer_aib_routes_over_rib_oper";
      type boolean;
      description
        "Prefer AIB routes over RIB/LSD operational state";
    }
    leaf mi-prefer-aib-routes-over-rib-cfg {
      xr:xr-xml-map "fib:mi_prefer_aib_routes_over_rib_cfg";
      type boolean;
      description "Prefer AIB routes over RIB/LSD configured state";
    }
    leaf-list mi-idb-ext-cleanup-failed-count {
      xr:xr-xml-map "fib:mi_idb_ext_cleanup_failed_count";
      type uint32;
      max-elements "3";
      description
        "Number of recycled idb extensions that failed
        cleanup";
    }
    leaf-list mi-lrpf-stats-fail {
      xr:xr-xml-map "fib:mi_lrpf_stats_fail";
      type uint32;
      max-elements "9";
      description "Per protocol Failure stats for label RPF";
    }
    leaf-list mi-lrpf-stats-act {
      xr:xr-xml-map "fib:mi_lrpf_stats_act";
      type uint32;
      max-elements "24";
      description "Per protocol actions stats for label RPF";
    }
    leaf-list mi-lrpf-num {
      xr:xr-xml-map "fib:mi_lrpf_num";
      type uint32;
      max-elements "3";
      description "Per protocol number of label RPFs";
    }
    leaf-list mi-idb-lsec-enabled-num {
      xr:xr-xml-map "fib:mi_idb_lsec_enabled_num";
      type uint32;
      max-elements "3";
      description
        "Number of interfaces having label security
        enabled";
    }
    leaf-list mi-num-lisp-eid {
      xr:xr-xml-map "fib:mi_num_lisp_eids";
      type uint32;
      max-elements "3";
      description "number of LISP EID prefixes";
    }
    leaf-list mi-num-lisp-valid-eid {
      xr:xr-xml-map "fib:mi_num_lisp_valid_eids";
      type uint32;
      max-elements "3";
      description
        "number of LISP EID prefixes eligible for
        forwarding";
    }
    leaf-list mi-cpuless-node {
      xr:xr-xml-map "fib:mi_cpuless_nodes";
      type uint32;
      max-elements "20";
      description "list of cpuless line cards";
    }

    list mi-proto-dbg-stat {
      description "Per protocol debug stats";
      uses FIB-SH-PROTO-DEBUG-STATS;
    }

    list mi-idb-purge-cntr {
      max-elements "3";
      description
        "the number of counters used for purge counter
        stats";
      uses FIB-SH-PROTO-PURGE-STATS;
    }

    list mi-del {
      description "Timestamps of deleted routes";
      uses FIB-SH-ROUTE-DEL-TS;
    }

    list mi-frr-stat {
      max-elements "3";
      description "FRR statistics";
      uses FIB-SH-PROTO-FRR-STATS;
    }
  }

  grouping FIB-SH-TBL-EXT-CLIENT-SUM {
    description "FIB external client summary information";

    container ses-pl-sum {
      description "ECD pathlist summary";
      uses FIB-SH-TBL-EXT-PL-SUM;
    }
    leaf ses-client-name {
      xr:xr-xml-map "fib:ses_client_name";
      type string;
      description "External client name";
    }
    leaf ses-feci-fib-proto {
      xr:xr-xml-map "fib:ses_feci_fib_proto";
      type uint32;
      description "Registration proto";
    }
    leaf ses-num-regs {
      xr:xr-xml-map "fib:ses_num_regs";
      type uint32;
      description "Number of registrations";
    }
    leaf ses-num-pending {
      xr:xr-xml-map "fib:ses_num_pending";
      type uint32;
      description "Number of pending notifs";
    }
    leaf ses-client-pulsed-time {
      xr:xr-xml-map "fib:ses_client_pulsed_time";
      type uint64;
      description "Client pulsed timestamp";
    }
    leaf ses-comp-id {
      xr:xr-xml-map "fib:ses_comp_id";
      type uint32;
      description "component-id of the client";
    }
    leaf ses-ecd-version {
      xr:xr-xml-map "fib:ses_ecd_version";
      type uint32;
      description "ECD version";
    }
  }

  grouping EVT-HIST-ENTRY {
    description "Event history Entry";
    leaf evt-timestamp {
      xr:xr-xml-map "fib:evt_timestamp";
      type string;
      description "The timestamp of the event";
    }
    leaf evt-name {
      xr:xr-xml-map "fib:evt_name";
      type string;
      description "Event name";
    }
    leaf evt-type {
      xr:xr-xml-map "fib:evt_type";
      type uint8;
      description "Event type";
    }
    leaf evt-many {
      xr:xr-xml-map "fib:evt_many";
      type boolean;
      description "Multiple instance flag";
    }
    leaf evt-sticky {
      xr:xr-xml-map "fib:evt_sticky";
      type boolean;
      description "Sticky flag";
    }
    leaf-list evt-data {
      xr:xr-xml-map "fib:evt_data";
      type uint32;
      description "Optional data";
    }
  }

  grouping EVT-HIST-INFO {
    description "Per object event history";
    leaf evt-class-name {
      xr:xr-xml-map "fib:evt_class_name";
      type string;
      description "Class name string";
    }

    list evt-entry {
      description "Array of event entries";
      uses EVT-HIST-ENTRY;
    }
  }

  grouping FIB-SH-INT-INTERNAL {
    description "FIB per interface internal information";

    container fib-idb-hist {
      description "Event History for IDB";
      uses EVT-HIST-INFO;
    }

    container fib-srte-head-hist {
      description "Event History for Srtehead";
      uses EVT-HIST-INFO;
    }
  }

  grouping FIB-SH-INT-DET {
    description "FIB per interface detail information";
    leaf interface-mtu {
      xr:xr-xml-map "fib:InterfaceMTU";
      type uint16;
      description "Interface Protocol MTU";
    }
    leaf forwarding-flag {
      xr:xr-xml-map "fib:ForwardingFlag";
      type boolean;
      description "Forwarding enabled/disabled flag";
    }
    leaf rpf-configured-flag {
      xr:xr-xml-map "fib:RPFConfiguredFlag";
      type boolean;
      description "RPF configured flag";
    }
    leaf rpf-mode {
      xr:xr-xml-map "fib:RPFMode";
      type Fib-rpf-mode;
      description "RPF mode";
    }
    leaf default-route-with-rpf {
      xr:xr-xml-map "fib:DefaultRouteWithRPF";
      type boolean;
      description "Allow default route with RPF";
    }
    leaf self-ping-with-rpf {
      xr:xr-xml-map "fib:SelfPingWithRPF";
      type boolean;
      description "Allow selfping with RPF";
    }
    leaf bgp-pa-input-configured-flag {
      xr:xr-xml-map "fib:BGP_PAInputConfiguredFlag";
      type boolean;
      description "BGP PA configured flag";
    }
    leaf source-bgp-pa-input-configured-flag {
      xr:xr-xml-map "fib:SourceBGP_PAInputConfiguredFlag";
      type boolean;
      description "src BGP PA configured flag";
    }
    leaf destination-bgp-pa-input-configured-flag {
      xr:xr-xml-map "fib:DestinationBGP_PAInputConfiguredFlag";
      type boolean;
      description "dst BGP PA configured flag";
    }
    leaf bgp-pa-output-configured-flag {
      xr:xr-xml-map "fib:BGP_PAOutputConfiguredFlag";
      type boolean;
      description "BGP PA configured flag";
    }
    leaf source-bgp-pa-output-configured-flag {
      xr:xr-xml-map "fib:SourceBGP_PAOutputConfiguredFlag";
      type boolean;
      description "src BGP PA configured flag";
    }
    leaf destination-bgp-pa-output-configured-flag {
      xr:xr-xml-map "fib:DestinationBGP_PAOutputConfiguredFlag";
      type boolean;
      description "dst BGP PA configured flag";
    }
    leaf icmp-flag {
      xr:xr-xml-map "fib:ICMPFlag";
      type uint32;
      description "ICMP  configured flag";
    }
    leaf multi-label-drop-flag {
      xr:xr-xml-map "fib:MultiLabelDropFlag";
      type boolean;
      description "Drop packets with multiple-label-stack if set";
    }
  }

  grouping FIB-SH-INT {
    description "FIB per interface information";

    container detail-fib-int-information {
      description "Detailed FIB interface information";
      uses FIB-SH-INT-DET;
    }

    container si-internal {
      description "Internal Information";
      uses FIB-SH-INT-INTERNAL;
    }
    leaf per-interface {
      xr:xr-xml-map "fib:PerInterface";
      type xr:Interface-name;
      description "Interface handle";
    }
    leaf fib-interface-type {
      xr:xr-xml-map "fib:FIBInterfaceType";
      type uint32;
      description "FIB Interface type";
    }
    leaf fib-id-pointer {
      xr:xr-xml-map "fib:FIB_IDPointer";
      type uint32;
      description "Pointer to fibidb";
    }
    leaf fib-id-flags {
      xr:xr-xml-map "fib:FIB_IDFlags";
      type uint32;
      description "Flags on fibidb";
    }
    leaf fib-id-extension-pointer {
      xr:xr-xml-map "fib:FIB_IDExtensionPointer";
      type uint32;
      description "Pointer to fibidb extension";
    }
    leaf fib-id-extension-flags {
      xr:xr-xml-map "fib:FIB_IDExtensionFlags";
      type uint32;
      description "Flags on fibidb extension";
    }
    leaf number-of-dependent-next-hop-information {
      xr:xr-xml-map "fib:NumberOfDependentNextHopInformation";
      type uint32;
      description "Number of dependent nhinfo's";
    }
    leaf vrf-local-cef-information-pointer {
      xr:xr-xml-map "fib:VRFLocalCEFInformationPointer";
      type uint32;
      description "Vrf local cef info ptr";
    }
    leaf reference-count {
      xr:xr-xml-map "fib:ReferenceCount";
      type uint16;
      description "Reference count";
    }
    leaf last-modified-time {
      xr:xr-xml-map "fib:LastModifiedTime";
      type uint32;
      description "Time last modified";
    }
    leaf last-operation {
      xr:xr-xml-map "fib:LastOperation";
      type Fibidb-oper;
      description "Last Oper";
    }
    leaf protocol-enabled {
      xr:xr-xml-map "fib:ProtocolEnabled";
      type boolean;
      description "Is the protocol configured?";
    }
    leaf referance-count-for-protocol {
      xr:xr-xml-map "fib:ReferanceCountForProtocol";
      type uint32;
      description "Reference count for the protocol";
    }
    leaf number-of-input-packets {
      xr:xr-xml-map "fib:NumberOfInputPackets";
      type uint64;
      description "Number of input packets";
    }
    leaf number-of-input-bytes {
      xr:xr-xml-map "fib:NumberOfInputBytes";
      type uint64;
      units "byte";
      description "Number of input bytes";
    }
    leaf number-of-output-packets {
      xr:xr-xml-map "fib:NumberOfOutputPackets";
      type uint64;
      description "Number of output packets";
    }
    leaf number-of-output-bytes {
      xr:xr-xml-map "fib:NumberOfOutputBytes";
      type uint64;
      units "byte";
      description "Number of output bytes";
    }
    leaf interface-up-flag {
      xr:xr-xml-map "fib:InterfaceUpFlag";
      type boolean;
      description "Interface up flag";
    }
    leaf per-packet-load-balancing-flag {
      xr:xr-xml-map "fib:PerPacketLoadBalancingFlag";
      type boolean;
      description "Per packet loadbalancing flag";
    }
    leaf p2p-interface-flag {
      xr:xr-xml-map "fib:P2PInterfaceFlag";
      type boolean;
      description "P2P interface flag";
    }
    leaf loopback-interface-flag {
      xr:xr-xml-map "fib:LoopbackInterfaceFlag";
      type boolean;
      description "Loopback interface flag";
    }
    leaf null-interface-flag {
      xr:xr-xml-map "fib:NullInterfaceFlag";
      type boolean;
      description "Null interface flag";
    }
    leaf tunnel-interface-flag {
      xr:xr-xml-map "fib:TunnelInterfaceFlag";
      type boolean;
      description "Tunnel interface flag";
    }
    leaf gre-tunnel-interface-flag {
      xr:xr-xml-map "fib:GRETunnelInterfaceFlag";
      type boolean;
      description "GRE Tunnel interface flag";
    }
    leaf punt-packets-from-fib-switching-flag {
      xr:xr-xml-map "fib:PuntPacketsFromFIBSwitchingFlag";
      type boolean;
      description "Punt packets from FIB switching flag";
    }
    leaf drop-packets-while-fib-switching-flag {
      xr:xr-xml-map "fib:DropPacketsWhileFIBSwitchingFlag";
      type boolean;
      description "Drop packets while FIB switching flag";
    }
    leaf punt-packets-from-linecard-flag {
      xr:xr-xml-map "fib:PuntPacketsFromLinecardFlag";
      type boolean;
      description "Punt packets from linecard flag";
    }
    leaf primary-ipv4-address {
      xr:xr-xml-map "fib:PrimaryIPV4Address";
      type string {
        length "0..52";
      }
      description "Pimary local v4 address for the interface";
    }
    leaf primary-ipv6-address {
      xr:xr-xml-map "fib:PrimaryIPV6Address";
      type string {
        length "0..52";
      }
      description "Pimary local v6 address for the interface";
    }
  }

  grouping FIB-PL-LDI-COUNT {
    description "FIB Pathlist and Loadinfo summary";
    leaf total-load-sharing-element-bytes {
      xr:xr-xml-map "fib:TotalLoadSharingElementBytes";
      type uint32;
      units "byte";
      description
        "Total memory used by load sharing elements in
        bytes";
    }
    leaf total-load-sharing-element-references {
      xr:xr-xml-map "fib:TotalLoadSharingElementReferences";
      type uint64;
      description
        "Total count of references to load sharing
        elements";
    }
    leaf total-path-list-elements {
      xr:xr-xml-map "fib:TotalPathListElements";
      type uint32;
      description "Total count of Pathlist elements";
    }
    leaf recursive-path-list-elements {
      xr:xr-xml-map "fib:RecursivePathListElements";
      type uint32;
      description "Count of recursive Pathlist elements";
    }
    leaf platform-shared-path-list-elements {
      xr:xr-xml-map "fib:PlatformSharedPathListElements";
      type uint32;
      description "Count of platform shared Pathlist elements";
    }
    leaf retry-path-list-elements {
      xr:xr-xml-map "fib:RetryPathListElements";
      type uint32;
      description "Count of Pathlist elements in retry";
    }
    leaf total-load-info-elements {
      xr:xr-xml-map "fib:TotalLoadInfoElements";
      type uint32;
      description "Total count of Loadinfo elements";
    }
    leaf recursive-load-info-elements {
      xr:xr-xml-map "fib:RecursiveLoadInfoElements";
      type uint32;
      description "Count of recursive Loadinfo elements";
    }
    leaf platform-shared-load-info-elements {
      xr:xr-xml-map "fib:PlatformSharedLoadInfoElements";
      type uint32;
      description "Count of platform shared Loadinfo elements";
    }
  }

  grouping FIB-SH-SUM {
    description "FIB summary statistics";

    container exclusive-load-sharing-element {
      description "Exclusive load sharing element";
      uses FIB-PL-LDI-COUNT;
    }

    container shared-load-sharing-element {
      description "Shared load sharing element";
      uses FIB-PL-LDI-COUNT;
    }

    container cross-shared-load-sharing-element {
      description "Cross-table shared load sharing element";
      uses FIB-PL-LDI-COUNT;
    }

    container label-shared-load-sharing-element {
      description "Label-shared load sharing element";
      uses FIB-PL-LDI-COUNT;
    }
    leaf prefix {
      xr:xr-xml-map "fib:Prefix";
      type yang:hex-string;
      description "The router-id";
    }
    leaf ss-tbl-id {
      xr:xr-xml-map "fib:ss_tbl_id";
      type uint32;
      description "Table Id";
    }
    leaf ss-tbl-id-ptr {
      xr:xr-xml-map "fib:ss_tbl_id_ptr";
      type uint32;
      description "Table Id Ptr";
    }
    leaf ss-vrf-id {
      xr:xr-xml-map "fib:ss_vrf_id";
      type uint32;
      description "Virtual routing forwarding instance Id";
    }
    leaf ss-vr-id {
      xr:xr-xml-map "fib:ss_vr_id";
      type uint32;
      description "Virtual router instance Id";
    }
    leaf load-balancing {
      xr:xr-xml-map "fib:LoadBalancing";
      type Ss-lba-state;
      description "LBA configuration state";
    }
    leaf forwarding-elements {
      xr:xr-xml-map "fib:ForwardingElements";
      type uint32;
      description
        "Number of forwarding elements linked to the
        table";
    }
    leaf routes {
      xr:xr-xml-map "fib:Routes";
      type uint32;
      description "Number of routes";
    }
    leaf prefix-in-place-modifications {
      xr:xr-xml-map "fib:PrefixInPlaceModifications";
      type uint32;
      description "Number of inplace modifications";
    }
    leaf stale-prefix-deletes {
      xr:xr-xml-map "fib:StalePrefixDeletes";
      type uint32;
      description "Number of deleted stale leafs";
    }
    leaf load-sharing-elements {
      xr:xr-xml-map "fib:LoadSharingElements";
      type uint32;
      description "Count of load sharing elements";
    }
    leaf load-sharing-references {
      xr:xr-xml-map "fib:LoadSharingReferences";
      type uint64;
      description "Count of load sharing references";
    }
    leaf total-load-share-element-bytes {
      xr:xr-xml-map "fib:TotalLoadShareElementBytes";
      type uint32;
      description "Total memory used by load sharing elements";
    }
    leaf leaves-used-bytes {
      xr:xr-xml-map "fib:LeavesUsedBytes";
      type uint32;
      description "Total memory used by leaves";
    }
    leaf reresolve-entries {
      xr:xr-xml-map "fib:ReresolveEntries";
      type uint32;
      description "Number of reresolved entries";
    }
    leaf old-unresolve-entries {
      xr:xr-xml-map "fib:OldUnresolveEntries";
      type uint32;
      description "Number of old unresolved entries";
    }
    leaf new-unresolve-entries {
      xr:xr-xml-map "fib:NewUnresolveEntries";
      type uint32;
      description "Number of new unresolved entries";
    }
    leaf unresolve-entries {
      xr:xr-xml-map "fib:UnresolveEntries";
      type uint32;
      description "Number of total unresolved entries";
    }
    leaf cef-route-drops {
      xr:xr-xml-map "fib:CEFRouteDrops";
      type uint32;
      description "Number of routes dropped by CEF";
    }
    leaf cef-version-mismatch-route-drops {
      xr:xr-xml-map "fib:CEFVersionMismatchRouteDrops";
      type uint64;
      description
        "the number of routes dropped due to version
        mismatch";
    }
    leaf delete-cache-num-entries {
      xr:xr-xml-map "fib:DeleteCacheNumEntries";
      type uint32;
      description "Number of entries in the route delete cache";
    }
    leaf existing-leaves-revisions {
      xr:xr-xml-map "fib:ExistingLeavesRevisions";
      type uint32;
      description "Number of entries present on addition";
    }
    leaf fib-default-prefix {
      xr:xr-xml-map "fib:FIBDefaultPrefix";
      type uint32;
      description "Default prefix";
    }
    leaf fib-default-prefix-mask-length {
      xr:xr-xml-map "fib:FIBDefaultPrefixMaskLength";
      type uint32;
      description "Default prefix mask length";
    }
    leaf next-hops {
      xr:xr-xml-map "fib:NextHops";
      type uint32;
      description "Number of NHINFOS";
    }
    leaf incomplete-next-hops {
      xr:xr-xml-map "fib:IncompleteNextHops";
      type uint32;
      description "Number of incomplete NHINFOS";
    }
    leaf resolution-timer {
      xr:xr-xml-map "fib:ResolutionTimer";
      type uint32;
      units "second";
      description "IP CEF resolution timer in seconds";
    }
    leaf slow-process-timer {
      xr:xr-xml-map "fib:SlowProcessTimer";
      type uint32;
      units "second";
      description "IP CEF slow processing time in seconds";
    }
    leaf max-resolution-timer {
      xr:xr-xml-map "fib:MaxResolutionTimer";
      type uint32;
      units "second";
      description "IP CEF max resolution time in seconds";
    }
    leaf imposition-prefixes {
      xr:xr-xml-map "fib:ImpositionPrefixes";
      type uint32;
      description "Number of prefixes with imposition LDI";
    }
    leaf extended-prefixes {
      xr:xr-xml-map "fib:ExtendedPrefixes";
      type uint32;
      description "Number of prefixes with extended path-list";
    }
    leaf cefl-bl-recycled-routes {
      xr:xr-xml-map "fib:CEFLBlRecycledRoutes";
      type uint32;
      description
        "Number of routes updates with recycled label
        handled";
    }
    leaf ldi-backwalks {
      xr:xr-xml-map "fib:LDIBackwalks";
      type uint32;
      description "pd backwalks on LDI modify with backup path";
    }
    leaf ss-prot-route-count {
      xr:xr-xml-map "fib:ss_prot_route_count";
      type uint32;
      description "Number of routes with FRR protection";
    }
    leaf lisp-eid-prefixes {
      xr:xr-xml-map "fib:LispEIDPrefixes";
      type uint32;
      description
        "Number of lisp eid prefixes associated with
        table";
    }
    leaf lisp-eid-valid-prefixes {
      xr:xr-xml-map "fib:LispEIDValidPrefixes";
      type uint32;
      description
        "Number of lisp eid prefixes eligible for
        forwarding";
    }
    leaf lisp-rloc-objects {
      xr:xr-xml-map "fib:LispRLOCObjects";
      type uint32;
      description
        "Number of lisp rloc objects associated with
        table";
    }
    leaf ss-vxlan-ltep-ifh {
      xr:xr-xml-map "fib:ss_vxlan_ltep_ifh";
      type xr:Interface-name;
      description "VXLAN local Interface handle";
    }
    leaf ss-drop-pl-count {
      xr:xr-xml-map "fib:ss_drop_pl_count";
      type uint32;
      description "Number of dropped pathlists";
    }
  }

  grouping FIB-SH-TBL-MPLS-LABEL-STACK {
    description
      "mpls label stack information for FIB table
      entries";
    leaf number-of-labels {
      xr:xr-xml-map "fib:NumberOfLabels";
      type uint32;
      description "NumberOfLabels";
    }
    leaf out-interface {
      xr:xr-xml-map "fib:OutInterface";
      type xr:Interface-name;
      description "OutInterface";
    }
    leaf nh-address {
      xr:xr-xml-map "fib:NHAddress";
      type string {
        length "0..52";
      }
      description "NHAddress";
    }
    leaf-list lstack {
      xr:xr-xml-map "fib:LStack";
      type uint32;
      max-elements "14";
      description "lstack";
    }
  }

  grouping FIB-SH-TBL-PATH-MPLS-INFO {
    description "mpls path information for FIB table entries";
    leaf local-lable {
      xr:xr-xml-map "fib:LocalLable";
      type uint32;
      description "LocalLable";
    }
    leaf recursive-fwd-chain {
      xr:xr-xml-map "fib:RecursiveFwdChain";
      type boolean;
      description "RecursiveFwdChain";
    }
    leaf recursive-out-label-valid {
      xr:xr-xml-map "fib:RecursiveOutLabelValid";
      type boolean;
      description "RecursiveOutLabelValid";
    }
    leaf recursive-out-lable {
      xr:xr-xml-map "fib:RecursiveOutLable";
      type uint32;
      description "RecursiveOutLable";
    }
    leaf number-of-igp-paths {
      xr:xr-xml-map "fib:NumberOfIGPPaths";
      type uint32;
      description "NumberOfIGPPaths";
    }
    leaf remote-backup {
      xr:xr-xml-map "fib:RemoteBackup";
      type boolean;
      description "RemoteBackupPath";
    }

    list igp-label-stack-array {
      description "igp label stack array";
      uses FIB-SH-TBL-MPLS-LABEL-STACK;
    }
  }

  grouping FIB-SH-IPENCAP-HDR-DET {
    description "Detailed IP Encap Header Description";
    leaf ip-encap-hdr-type {
      xr:xr-xml-map "fib:IPEncapHdrType";
      type Fib-sh-ipencap-hdr;
      description "Header Type";
    }
    leaf ip-encap-hdrp {
      xr:xr-xml-map "fib:IPEncapHdrp";
      type yang:hex-string;
      description "Static Header";
    }
    leaf ip-encap-hdr-dyn {
      xr:xr-xml-map "fib:IPEncapHdrDyn";
      type uint32;
      description "Dynamic Header Fields";
    }
  }

  grouping FIB-SH-IPENCAP-DET {
    description "Detailed IP Encap Description";
    leaf ip-encap-hdr-count {
      xr:xr-xml-map "fib:IPEncapHdrCount";
      type uint8;
      description "Header Count";
    }
    leaf ip-encap-locks {
      xr:xr-xml-map "fib:IPEncapLocks";
      type uint32;
      description "IPEncap Object Locks";
    }
    leaf ip-encap-transport-tbl {
      xr:xr-xml-map "fib:IPEncapTransportTbl";
      type uint32;
      description "Transport Table";
    }
    leaf ipe-transport-vrf-name {
      xr:xr-xml-map "fib:ipe_transport_vrf_name";
      type string;
      description "Transport VRF name";
    }
    leaf ip-encap-transport-af {
      xr:xr-xml-map "fib:IPEncapTransportAf";
      type uint32;
      description "Transport AF";
    }
    leaf ip-encap-payload-af {
      xr:xr-xml-map "fib:IPEncapPayloadAf";
      type uint32;
      description "Payload AF";
    }
    leaf ip-encap-payload-mtu {
      xr:xr-xml-map "fib:IPEncapPayloadMtu";
      type uint16;
      description "Payload MTU";
    }
    leaf ip-encap-parent {
      xr:xr-xml-map "fib:IPEncapParent";
      type uint32;
      description "Pointer to parent";
    }
    leaf ip-encap-parent-type {
      xr:xr-xml-map "fib:IPEncapParentType";
      type uint32;
      description "Parent type enumeration";
    }

    list ip-encap-hdr {
      description "Headers";
      uses FIB-SH-IPENCAP-HDR-DET;
    }
  }

  grouping FIB-SH-TBL-PATH-DET {
    description "Detailed path information for FIB table entries";
    leaf ip-address-to-recurse {
      xr:xr-xml-map "fib:IPAddressToRecurse";
      type string {
        length "0..52";
      }
      description "IP address to recurse to";
    }
    leaf label-to-recurse {
      xr:xr-xml-map "fib:LabelToRecurse";
      type uint32;
      description "Local label to recurse over";
    }
    leaf detail-next-hop-prefix {
      xr:xr-xml-map "fib:DetailNextHopPrefix";
      type string {
        length "0..52";
      }
      description "Next hop prefix";
    }
    leaf next-hop-mask-length {
      xr:xr-xml-map "fib:NextHopMaskLength";
      type uint8;
      description "Next hop mask length";
    }
    leaf interface-associated-path {
      xr:xr-xml-map "fib:InterfaceAssociatedPath";
      type xr:Interface-name;
      description "Interface associated with this path";
    }
    leaf next-hop-interface {
      xr:xr-xml-map "fib:NextHopInterface";
      type xr:Interface-name;
      description "Next hop interface";
    }
    leaf next-hop-vrf {
      xr:xr-xml-map "fib:NextHopVRF";
      type string {
        length "0..33";
      }
      description "Next hop VRF";
    }
    leaf tunnle-endpoint-id {
      xr:xr-xml-map "fib:TunnleEndpointID";
      type uint32;
      description "Tunnel endpoint id";
    }
    leaf lisprlocid {
      xr:xr-xml-map "fib:LISPRLOCID";
      type uint32;
      description "LISP RLOC ID";
    }
    leaf number-of-dependencies-this-path {
      xr:xr-xml-map "fib:NumberOfDependenciesThisPath";
      type uint32;
      description "No. of dependents for this path";
    }
    leaf robin-reset-value {
      xr:xr-xml-map "fib:RobinResetValue";
      type uint8;
      description "Round robin reset value";
    }
    leaf recurse-prefix-object {
      xr:xr-xml-map "fib:RecursePrefixObject";
      type boolean;
      description "Is recursion object a leaf?";
    }
    leaf next-prefix-recursion {
      xr:xr-xml-map "fib:NextPrefixRecursion";
      type yang:hex-string;
      description "Next prefix recursion in the path";
    }
    leaf next-prefix-length {
      xr:xr-xml-map "fib:NextPrefixLength";
      type uint8;
      description "Next prefix length";
    }
    leaf recurse-prefix-object2 {
      xr:xr-xml-map "fib:RecursePrefixObject2";
      type boolean;
      description
        "Recursion has two leaves (e.g. implicit-null
        path)";
    }
    leaf next-prefix-recursion2 {
      xr:xr-xml-map "fib:NextPrefixRecursion2";
      type yang:hex-string;
      description "Next prefix2 recursion in the path";
    }
    leaf next-prefix-length2 {
      xr:xr-xml-map "fib:NextPrefixLength2";
      type uint8;
      description "Next prefix2 length";
    }
    leaf detail-fib-adjacency-type {
      xr:xr-xml-map "fib:DetailFIBAdjacencyType";
      type Fib-adjacency-show;
      description "FIB entry adjacency type";
    }
    leaf current-path-flag {
      xr:xr-xml-map "fib:CurrentPathFlag";
      type boolean;
      description "Current path flag";
    }
    leaf recursive-path-information {
      xr:xr-xml-map "fib:RecursivePathInformation";
      type boolean;
      description "Recursive path information is available";
    }
    leaf external-adjacency {
      xr:xr-xml-map "fib:ExternalAdjacency";
      type boolean;
      description "Path is an external adjacency";
    }
    leaf fib-path-nh-information-type {
      xr:xr-xml-map "fib:FIBPathNHInformationType";
      type Fib-neh;
      description "FIB Nhinfo type";
    }
    leaf fib-path-nh-information-type-special {
      xr:xr-xml-map "fib:FIBPathNHInformationTypeSpecial";
      type Fib-neh-special;
      description "FIB Nhinfo type special";
    }
    leaf weight-of-path {
      xr:xr-xml-map "fib:WeightOfPath";
      type uint32;
      description "Weight of the path";
    }
    leaf tunnel-class {
      xr:xr-xml-map "fib:TunnelClass";
      type uint8;
      description "Tunnel class of the path";
    }
    leaf tunnel-is-forward-class {
      xr:xr-xml-map "fib:TunnelIsForwardClass";
      type boolean;
      description "Tunnel is forward class";
    }

    list spd-ipencap {
      description "IP Encap";
      uses FIB-SH-IPENCAP-DET;
    }
  }

  grouping FIB-SH-TBL-PATH {
    description "Brief path information for FIB table entries";

    list fib-sh-tbl-path {
      description "fib sh tbl path";

      container more-detail-about-path {
        description "More detail about this path entry";
        uses FIB-SH-TBL-PATH-DET;
      }

      container mpls-information-for-path {
        description "mpls info for this path entry";
        uses FIB-SH-TBL-PATH-MPLS-INFO;
      }
      leaf hardware-information {
        type yang:hex-string;
        description "Hardware info";
      }
      leaf brief-interface-handle {
        type xr:Interface-name;
        description "Interface handle";
      }
      leaf brief-next-hop-prefix {
        type string {
          length "0..52";
        }
        description "Next hop prefix";
      }
      leaf via-label-to-recurse {
        type uint32;
        description "Local label to recurse over";
      }
      leaf brief-pnode-address {
        type string {
          length "0..52";
        }
        description "P-node address";
      }
      leaf brief-qnode-address {
        type string {
          length "0..52";
        }
        description "Q-node address";
      }
      leaf resolved-path {
        type boolean;
        description "Resolved path";
      }
      leaf recursive-path {
        type boolean;
        description "Recursive path";
      }
      leaf packets-received-path {
        type boolean;
        description "Packets received on this path";
      }
      leaf attached-path {
        type boolean;
        description "Attached path";
      }
      leaf backup-path {
        type boolean;
        description "Backup path";
      }
      leaf best-external-path {
        type boolean;
        description "Best external path";
      }
      leaf protect-ignore {
        type boolean;
        description "Is protection ignored";
      }
      leaf path-dlb {
        type boolean;
        description "Is this the path used for DLB";
      }
      leaf path-flags {
        type uint16;
        description "Path flags";
      }
      leaf path-info-flags {
        type uint16;
        description "Path Info flags";
      }
      leaf path-index {
        type uint8;
        description "Path index";
      }
      leaf backup-index {
        type uint8;
        description "Backup path index";
      }
      leaf next-hop-index {
        type uint32;
        description "Next Hop Index";
      }
      leaf parent-interface-handle {
        type xr:Interface-name;
        description "Parent Interface Handle";
      }
      leaf recursionvia-len {
        type uint8;
        description "recursion via /N constraint";
      }
    }
  }

  grouping FIB-ADDR-STR {
    description "FIB address";
    leaf address {
      xr:xr-xml-map "fib:address";
      type string {
        length "0..60";
      }
      description "address";
    }
  }

  grouping FIB-SH-TBL-LOADINFO-INT {
    description
      "Internal load sharing information arrays for FIB
      table entries";
    leaf level-ofldis {
      xr:xr-xml-map "fib:LevelOFLDIS";
      type uint8;
      description "level of ldis";
    }
    leaf number-of-ldis {
      xr:xr-xml-map "fib:NumberOfLDIS";
      type uint8;
      description "no. of ldis";
    }
    leaf maximum-index-arrays {
      xr:xr-xml-map "fib:MaximumIndexArrays";
      type uint32;
      description "Maximum index of the arrays";
    }
    leaf path-indices {
      xr:xr-xml-map "fib:PathIndices";
      type yang:hex-string;
      description "Path indices";
    }
    leaf path-ldi-numbers {
      xr:xr-xml-map "fib:PathLDINumbers";
      type yang:hex-string;
      description "Path indices";
    }
    leaf maximum-slots {
      xr:xr-xml-map "fib:MaximumSlots";
      type uint32;
      description "Maximum slots";
    }
    leaf normalized-weights {
      xr:xr-xml-map "fib:NormalizedWeights";
      type yang:hex-string;
      description "Normalized weights";
    }
    leaf tunnel-class-value {
      xr:xr-xml-map "fib:TunnelClassValue";
      type yang:hex-string;
      description "Tunnel class value";
    }
    leaf is-pbts-info-valid {
      xr:xr-xml-map "fib:IsPBTSInfoValid";
      type boolean;
      description "PBTS info valid flag";
    }
    leaf pbts-class-offset {
      xr:xr-xml-map "fib:PBTSClassOffset";
      type yang:hex-string;
      description "PBTS class offset";
    }
    leaf pbts-class-num-paths {
      xr:xr-xml-map "fib:PBTSClassNumPaths";
      type yang:hex-string;
      description "PBTS class num paths";
    }
    leaf pbts-fallback-mapped-class {
      xr:xr-xml-map "fib:PBTSFallbackMappedClass";
      type yang:hex-string;
      description "PBTS class falls back to class";
    }
    leaf round-robin-disable {
      xr:xr-xml-map "fib:RoundRobinDisable";
      type boolean;
      description "Round Robin Disable";
    }
    leaf ldi-next-hop-buckets {
      xr:xr-xml-map "fib:LDINextHopBuckets";
      type uint8;
      description "Number of LDI next hop buckets";
    }
    leaf platform-hardware-information {
      xr:xr-xml-map "fib:PlatformHardwareInformation";
      type yang:hex-string;
      description "Platform Hardware info";
    }
    leaf-list sanity-flag {
      xr:xr-xml-map "fib:SanityFlag";
      type boolean;
      description "Sanity flag";
    }
    leaf-list interface-handle {
      xr:xr-xml-map "fib:InterfaceHandle";
      type xr:Interface-name;
      description "Interface handle";
    }
    leaf-list weights-of-path {
      xr:xr-xml-map "fib:WeightsOfPaths";
      type uint32;
      description "Weights of paths";
    }

    list adjacency-address {
      description "Adjacency address";
      uses FIB-ADDR-STR;
    }

    list pbts-class-is-fallback-mapped {
      min-elements "9";
      max-elements "9";
      description "Does PBTS class fall back to drop or any class";
      leaf entry {
        type boolean;
        description "Array entry.";
      }
    }

    list pbts-fallback-to-drop {
      min-elements "9";
      max-elements "9";
      description "PBTS class falls back to drop";
      leaf entry {
        type boolean;
        description "Array entry.";
      }
    }

    list tunnel-is-forward-class {
      min-elements "128";
      max-elements "128";
      description "Tunnel is forward class";
      leaf entry {
        type boolean;
        description "Array entry.";
      }
    }
  }

  grouping FIB-SH-TBL-LOADINFO-DET {
    description
      "Detailed load sharing information for FIB table
      entries";

    container load-informtion-internal-data {
      description "Loadinfo internal data";
      uses FIB-SH-TBL-LOADINFO-INT;
    }
    leaf packets-through-load-information {
      xr:xr-xml-map "fib:PacketsThroughLoadInformation";
      type uint64;
      description "Packets through this loadinfo";
    }
    leaf bytes-through-load-information {
      xr:xr-xml-map "fib:BytesThroughLoadInformation";
      type uint64;
      units "byte";
      description "Bytes through this loadinfo";
    }
    leaf total-packets-through-load-information {
      xr:xr-xml-map "fib:TotalPacketsThroughLoadInformation";
      type uint64;
      description "Total packets through this loadinfo";
    }
    leaf total-bytes-through-load-information {
      xr:xr-xml-map "fib:TotalBytesThroughLoadInformation";
      type uint64;
      units "byte";
      description "Total bytes through this loadinfo";
    }
    leaf prefix-of-owner {
      xr:xr-xml-map "fib:PrefixOfOwner";
      type uint32;
      description "Prefix of the owner";
    }
    leaf mask-length-of-owner {
      xr:xr-xml-map "fib:MaskLengthOfOwner";
      type uint32;
      description "Mask length of the owner";
    }
    leaf load-information-reference-count {
      xr:xr-xml-map "fib:LoadInformationReferenceCount";
      type uint16;
      description "Loadinfo reference count";
    }
    leaf per-dest-load-sharing-flag {
      xr:xr-xml-map "fib:PerDestLoadSharingFlag";
      type boolean;
      description "Per destination load sharing flag";
    }
    leaf load-information-owner-deleted-flag {
      xr:xr-xml-map "fib:LoadInformationOwnerDeletedFlag";
      type boolean;
      description "Loadinfo owner deleted flag";
    }
    leaf loadinfo-sanity-flag {
      xr:xr-xml-map "fib:LoadinfoSanityFlag";
      type boolean;
      description "Loadinfo sanity flag";
    }
    leaf is-owner {
      xr:xr-xml-map "fib:IsOwner";
      type boolean;
      description "Owner flag";
    }
  }

  grouping FIB-SH-TBL-FIB-DET {
    description "Detailed FIB table entry information";

    container loadshare-information {
      description "Detailed Loadshare info";
      uses FIB-SH-TBL-LOADINFO-DET;
    }
    leaf fib-entry-version {
      xr:xr-xml-map "fib:FIBEntryVersion";
      type uint32;
      description "FIB entry version number";
    }
    leaf per-prefix-accounting {
      xr:xr-xml-map "fib:PerPrefixAccounting";
      type uint8;
      description "Per Prefix Accounting";
    }
    leaf load-sharing-type {
      xr:xr-xml-map "fib:LoadSharingType";
      type Fib-loadshare-show;
      description "Load sharing type";
    }
    leaf fib-entry-adjacency-type {
      xr:xr-xml-map "fib:FIBEntryAdjacencyType";
      type Fib-adjacency-show;
      description "FIB entry adjacency type";
    }
    leaf fib-protocol-type {
      xr:xr-xml-map "fib:FIBProtocolType";
      type uint32;
      description "FIB Protocol type";
    }
    leaf afi-fib-protocol-type {
      xr:xr-xml-map "fib:AFI_FIB_ProtocolType";
      type uint32;
      description "AFI FIB protocol type";
    }
    leaf aib-l3-address {
      xr:xr-xml-map "fib:AIB_L3_Address";
      type yang:hex-string;
      description "AIB L3 Address";
    }
    leaf adjacency-address-length {
      xr:xr-xml-map "fib:AdjacencyAddressLength";
      type uint32;
      description "ADJ ADDR LEN";
    }
    leaf adjacency-interface {
      xr:xr-xml-map "fib:AdjacencyInterface";
      type uint32;
      description "ADJ IFH";
    }
    leaf fib-special-nh-information-type {
      xr:xr-xml-map "fib:FIBSpecialNHInformationType";
      type uint32;
      description "FIB Special NHINFO Type";
    }
    leaf fib-entry-adjacency-address {
      xr:xr-xml-map "fib:FIBEntryAdjacencyAddress";
      type yang:hex-string;
      description "FIB entry adj address";
    }
    leaf fib-entry-adjacency-interface {
      xr:xr-xml-map "fib:FIBEntryAdjacencyInterface";
      type uint32;
      description "FIB entry adjacency interface";
    }
    leaf packets-through-fib-entry {
      xr:xr-xml-map "fib:PacketsThroughFIBEntry";
      type uint64;
      description "Packets through this FIB entry";
    }
    leaf bytes-through-fib-entry {
      xr:xr-xml-map "fib:BytesThroughFIBEntry";
      type uint64;
      units "byte";
      description "Bytes through this FIB entry";
    }
    leaf detailed-prefix-length {
      xr:xr-xml-map "fib:DetailedPrefixLength";
      type uint32;
      description "Prefix length";
    }
    leaf prefix-protocol {
      xr:xr-xml-map "fib:PrefixProtocol";
      type uint32;
      description "Prefix protocol";
    }
    leaf precedence-forpackets {
      xr:xr-xml-map "fib:PrecedenceForpackets";
      type uint8;
      description "Precedence for packets to this entry";
    }
    leaf traffic-index-for-packets {
      xr:xr-xml-map "fib:TrafficIndexForPackets";
      type uint8;
      description "Traffic index for packets to this entry";
    }
    leaf switch-compontent-id {
      xr:xr-xml-map "fib:SwitchCompontentID";
      type uint32;
      description "Switch function compontent ID";
    }
    leaf fast-adjacency-flag {
      xr:xr-xml-map "fib:FastAdjacencyFlag";
      type boolean;
      description "Fast adjacency flag";
    }
    leaf illegal-fast-adjacency-flag {
      xr:xr-xml-map "fib:IllegalFastAdjacencyFlag";
      type boolean;
      description "Illegal fast adjacency flag";
    }
    leaf remote-adjacency-flag {
      xr:xr-xml-map "fib:RemoteAdjacencyFlag";
      type boolean;
      description "Remote adjacency flag";
    }
    leaf bgp-attribute-id {
      xr:xr-xml-map "fib:BGPAttributeID";
      type uint32;
      description "BGP attribute id";
    }
    leaf bgp-local-attribute-id {
      xr:xr-xml-map "fib:BGPLocalAttributeID";
      type uint32;
      description "BGP local attribute id";
    }
    leaf bgp-attribute-origin-as {
      xr:xr-xml-map "fib:BGPAttributeOriginAS";
      type uint32;
      description "BGP attribute origin as";
    }
    leaf bgp-attribute-next-hop-as {
      xr:xr-xml-map "fib:BGPAttributeNextHopAS";
      type uint32;
      description "BGP attribute next hop as";
    }
    leaf path-string {
      xr:xr-xml-map "fib:PathString";
      type yang:hex-string;
      description "As path string";
    }
    leaf extcom-string {
      xr:xr-xml-map "fib:ExtcomString";
      type yang:hex-string;
      description "extcom st";
    }
    leaf com-string {
      xr:xr-xml-map "fib:ComString";
      type yang:hex-string;
      description "com st";
    }
    leaf extended-community {
      xr:xr-xml-map "fib:ExtendedCommunity";
      type uint32;
      description "extended community";
    }
    leaf qos-group {
      xr:xr-xml-map "fib:QOSGroup";
      type uint32;
      description "qos group";
    }
    leaf mpls-fec {
      xr:xr-xml-map "fib:MPLSFec";
      type uint32;
      description "mpls fec";
    }
    leaf qppb-qos-group-and-ip-precedence {
      xr:xr-xml-map "fib:QPPB_QOSGroupAndIPPrecedence";
      type uint32;
      description "qppb QOS group and IP precedence";
    }
    leaf flow-tag {
      xr:xr-xml-map "fib:FlowTag";
      type uint8;
      description "PBR flow-tag";
    }
    leaf forward-class {
      xr:xr-xml-map "fib:ForwardClass";
      type uint8;
      description "SPP forwarding class ID";
    }
    leaf pl-time-of-last-update-in-msec {
      xr:xr-xml-map "fib:PLTimeOfLastUpdateInMsec";
      type uint64;
      description "The time of last update for PL in msec";
    }
    leaf ldi-time-of-last-update-in-msec {
      xr:xr-xml-map "fib:LDITimeOfLastUpdateInMsec";
      type uint64;
      description "The time of last update for LDI in msec";
    }
    leaf lwldi-time-of-last-update-in-msec {
      xr:xr-xml-map "fib:LWLDITimeOfLastUpdateInMsec";
      type uint64;
      description "The time of last update for LW-LDI in msec";
    }
    leaf pl-time-stamp-type {
      xr:xr-xml-map "fib:PLTimeStampType";
      type uint32;
      description "The type of time-stamp on PL";
    }
  }

  grouping FIB-SH-TBL-FIB {
    description "Basic FIB table information";

    container detail-fib-entry-information {
      description "Detailed FIB entry information";
      uses FIB-SH-TBL-FIB-DET;
    }

    container fib-entry-path {
      description "FIB entry path details";
      uses FIB-SH-TBL-PATH;
    }
    leaf protocol-type-fib-entry {
      xr:xr-xml-map "fib:ProtocolTypeFIBEntry";
      type uint32;
      description "Proto type for this entry";
    }
    leaf platform-hardware {
      xr:xr-xml-map "fib:PlatformHardware";
      type yang:hex-string;
      description "Platform Hardware info";
    }
    leaf number-of-referances-to-path-list {
      xr:xr-xml-map "fib:NumberOfReferancesToPathList";
      type uint32;
      description "Number of references to the pathlist";
    }
    leaf path-list-flags {
      xr:xr-xml-map "fib:PathListFlags";
      type uint32;
      description "The pathlist flags";
    }
    leaf path-list-source {
      xr:xr-xml-map "fib:PathListSource";
      type uint32;
      description "The pathlist source";
    }
    leaf number-of-referances-to-ldi {
      xr:xr-xml-map "fib:NumberOfReferancesToLDI";
      type uint32;
      description "Number of references to the LDI";
    }
    leaf ldi-flags {
      xr:xr-xml-map "fib:LDIFlags";
      type uint32;
      description "The LDI flags";
    }
    leaf flags-external-ldi {
      xr:xr-xml-map "fib:FlagsExternalLDI";
      type uint32;
      description "The flags of ext assocaited with LDI ";
    }
    leaf exact-route-result {
      xr:xr-xml-map "fib:ExactRouteResult";
      type boolean;
      description "exact-route result";
    }
    leaf prefix-is-static-or-connected {
      xr:xr-xml-map "fib:PrefixIsStaticOrConnected";
      type boolean;
      description "Prefix is static or connected";
    }
    leaf packet-should-recieve {
      xr:xr-xml-map "fib:PacketShouldRecieve";
      type boolean;
      description "Packet should always be received";
    }
    leaf prefix-connected {
      xr:xr-xml-map "fib:PrefixConnected";
      type boolean;
      description "Prefix is connected";
    }
    leaf prefix-for-adjancency {
      xr:xr-xml-map "fib:PrefixForAdjancency";
      type boolean;
      description "Prefix is for an adjacency";
    }
    leaf prefix-for-pic-next-hop {
      xr:xr-xml-map "fib:PrefixForPICNextHop";
      type boolean;
      description "Prefix is for a PIC nexthop";
    }
    leaf purgable-after-purge-interval {
      xr:xr-xml-map "fib:PurgableAfterPurgeInterval";
      type boolean;
      description "Purgable after the purge interval";
    }
    leaf broadcast-recive-flag {
      xr:xr-xml-map "fib:BroadcastReciveFlag";
      type boolean;
      description "Broadcast receive flag";
    }
    leaf broadcast-forward-flag {
      xr:xr-xml-map "fib:BroadcastForwardFlag";
      type boolean;
      description "Broadcast forward flag";
    }
    leaf zero-by-zero-route-as-default {
      xr:xr-xml-map "fib:ZeroByZeroRouteAsDefault";
      type boolean;
      description "0/0 route added as default route";
    }
    leaf external-switch-triggered {
      xr:xr-xml-map "fib:ExternalSwitchTriggered";
      type boolean;
      description "External switch function triggered";
    }
    leaf route-attribute-flag {
      xr:xr-xml-map "fib:RouteAttributeFlag";
      type boolean;
      description "Route attributes summary flag";
    }
    leaf dummy-real-zero-route {
      xr:xr-xml-map "fib:DummyRealZeroRoute";
      type boolean;
      description "Dummy real zero route";
    }
    leaf ldi-lw-flag {
      xr:xr-xml-map "fib:LDI_LWFlag";
      type uint32;
      description "The LDI LW flags";
    }
    leaf ref-counter-of-ldi-lw-ldi {
      xr:xr-xml-map "fib:RefCounterOfLDI_LW_LDI";
      type uint32;
      description "The refcounter of LDI LW LDI";
    }
    leaf type-of-ldi-lw-ldi {
      xr:xr-xml-map "fib:TypeOfLDI_LW_LDI";
      type uint32;
      description "The type of LDI LW LDI";
    }
    leaf lspa-flags {
      xr:xr-xml-map "fib:LSPAFlags";
      type uint32;
      description "The LSPA flags";
    }
    leaf version-of-route {
      xr:xr-xml-map "fib:VersionOfRoute";
      type uint64;
      description "The version of the route";
    }
    leaf fib-route-download-priority {
      xr:xr-xml-map "fib:FIBRouteDownloadPriority";
      type uint32;
      description "Priority at which the route was downloaded";
    }
    leaf time-of-last-update-in-msec {
      xr:xr-xml-map "fib:TimeOfLastUpdateInMsec";
      type uint64;
      description "The time of last update in msec";
    }
    leaf l2-subscriber-route {
      xr:xr-xml-map "fib:L2SubscriberRoute";
      type boolean;
      description "Is L2 Subscriber route";
    }
    leaf l2-subscriber-xconnect-id {
      xr:xr-xml-map "fib:L2SubscriberXConnectId";
      type uint32;
      description "XConnect-id associated with L2 subscriber";
    }
    leaf l2-subscriber-ip-protocol {
      xr:xr-xml-map "fib:L2SubscriberIPProtocol";
      type uint32;
      description "IP protocol associated with L2 subscriber";
    }
    leaf l2tpv3-cookie-length-bits {
      xr:xr-xml-map "fib:L2TPV3CookieLengthBits";
      type uint32;
      description "L2TPv3 cookie length for L2 subscriber";
    }
    leaf route-for-external-reach-linecard-flag {
      xr:xr-xml-map "fib:RouteForExternalReachLinecardFlag";
      type boolean;
      description
        "Route destined for Line Card that support
        External Reach only";
    }
  }

  grouping FIB-SH-TIMESPEC {
    description "FIB SH TIMESPEC";
    leaf seconds {
      xr:xr-xml-map "fib:Seconds";
      type int32;
      description "Seconds";
    }
    leaf nano-seconds {
      xr:xr-xml-map "fib:NanoSeconds";
      type int32;
      description "NanoSeconds";
    }
  }

  grouping FIB-SH-FRR-LOG {
    description "FIB frr log information";

    container frr-timestamp {
      description "frr timestamp";
      uses FIB-SH-TIMESPEC;
    }
    leaf frr-protocol-type {
      xr:xr-xml-map "fib:FRRProtocolType";
      type Fib-frr-protocol-show;
      description "FIB Protocol Type";
    }
    leaf frr-interface-name {
      xr:xr-xml-map "fib:FRRInterfaceName";
      type xr:Interface-name;
      description "Interface assoc w frr nh";
    }
    leaf frr-prefix {
      xr:xr-xml-map "fib:FRRPrefix";
      type string {
        length "0..52";
      }
      description "nh prefix";
    }
    leaf frr-switching-time {
      xr:xr-xml-map "fib:FRRSwitchingTime";
      type uint32;
      description "frr switching time";
    }
    leaf bundle-member-interface-name {
      xr:xr-xml-map "fib:BundleMemberInterfaceName";
      type xr:Interface-name;
      description "bundle member";
    }
  }

  grouping FIB-SH-TBL-EXT-PL-SUM {
    description "FIB external client pathlist summary";
    leaf sep-num-ecd-pathlist {
      xr:xr-xml-map "fib:sep_num_ecd_pathlist";
      type uint32;
      description "Number of ECD pathlists";
    }
    leaf sep-num-ecd-pl-unresolved {
      xr:xr-xml-map "fib:sep_num_ecd_pl_unresolved";
      type uint32;
      description "Number of ECD pathlists unresolved";
    }
    leaf-list sep-num-ecd-pl-per-interest {
      xr:xr-xml-map "fib:sep_num_ecd_pl_per_interest";
      type uint32;
      max-elements "12";
      description "Number of ECD pathlists per interest";
    }
  }

  grouping FIB-SH-TBL-EXT-SUM-ALL {
    description
      "FIB external brief summary information across all
      clients";

    container sesa-pl-sum {
      description "External pathlist summary";
      uses FIB-SH-TBL-EXT-PL-SUM;
    }
    leaf sesa-num-client {
      xr:xr-xml-map "fib:sesa_num_client";
      type uint32;
      description "Client information";
    }
  }

  grouping FIB-ISSU-PROTO-STATE {
    description "FIB ISSU protocol state";
    leaf protocol-name {
      xr:xr-xml-map "fib:ProtocolName";
      type string {
        length "0..6";
      }
      description "Protocol name";
    }
    leaf aib-eod-time-stamp {
      xr:xr-xml-map "fib:AIB_EODTimeStamp";
      type string {
        length "0..33";
      }
      description "AIB EODTimeStamp";
    }
    leaf rsi-eod-valid {
      xr:xr-xml-map "fib:RSI_EODValid";
      type boolean;
      description "RSI EOD expected/valid";
    }
    leaf rsi-eod-time-stamp {
      xr:xr-xml-map "fib:RSI_EODTimeStamp";
      type string {
        length "0..33";
      }
      description "RSI EOD received timestamp";
    }
    leaf lsd-eod-valid {
      xr:xr-xml-map "fib:LSD_EODValid";
      type boolean;
      description "LSD EOD expected/valid";
    }
    leaf lsd-eod-time-stamp {
      xr:xr-xml-map "fib:LSD_EODTimeStamp";
      type string {
        length "0..33";
      }
      description "LSD EOD received timestamp";
    }
    leaf lmrib-eod-valid {
      xr:xr-xml-map "fib:LMRIB_EODValid";
      type boolean;
      description "LMRIB EOD expected/valid";
    }
    leaf lmrib-eod-time-stamp {
      xr:xr-xml-map "fib:LMRIB_EODTimeStamp";
      type string {
        length "0..33";
      }
      description "LMRIB EOD received timestamp";
    }
    leaf rib-info-valid {
      xr:xr-xml-map "fib:RIB_InfoValid";
      type boolean;
      description "RIB table info valid";
    }
    leaf bcdl-tables {
      xr:xr-xml-map "fib:BCDLTables";
      type uint32;
      description "Number of BCDL tables";
    }
    leaf converged-tables {
      xr:xr-xml-map "fib:ConvergedTables";
      type uint32;
      description "Number of tables converged";
    }
    leaf rib-tables-converged-time-stamp {
      xr:xr-xml-map "fib:RIBTablesConvergedTimeStamp";
      type string {
        length "0..33";
      }
      description "All RIB tables converged timestamp";
    }
    leaf protocol-eod-valid {
      xr:xr-xml-map "fib:ProtocolEODValid";
      type boolean;
      description "Protocol EOD expected/valid";
    }
    leaf protocol-eod-time-stamp {
      xr:xr-xml-map "fib:ProtocolEODTimeStamp";
      type string {
        length "0..33";
      }
      description "Protocol EOD sent timestamp";
    }
  }

  grouping FIB-ISSU-STATE {
    description "FIB ISSU state";
    leaf imdr-support {
      xr:xr-xml-map "fib:IMDRSupport";
      type boolean;
      description "IMDR supported";
    }
    leaf slc-support {
      xr:xr-xml-map "fib:SLCSupport";
      type boolean;
      description "SLC supported";
    }
    leaf fis-issu-restart {
      xr:xr-xml-map "fib:fis_issu_restart";
      type boolean;
      description "ISSU restart";
    }
    leaf imdr-eoc-implicit {
      xr:xr-xml-map "fib:IMDREocImplicit";
      type boolean;
      description "IMDR End-of-config implicit";
    }
    leaf slc-eoc-implicit {
      xr:xr-xml-map "fib:SLCEocImplicit";
      type boolean;
      description "SLC End-of-config implicit";
    }
    leaf eoc-received-imdr-time-stamp {
      xr:xr-xml-map "fib:EOCReceivedIMDRTimeStamp";
      type string {
        length "0..33";
      }
      description "End-of-config received from IMDR timestamp";
    }
    leaf eoc-received-slc-time-stamp {
      xr:xr-xml-map "fib:EOCReceivedSLCTimeStamp";
      type string {
        length "0..33";
      }
      description "End-of-config received from SLC timestamp";
    }
    leaf eod-received-im-time-stamp {
      xr:xr-xml-map "fib:EODReceivedIMTimeStamp";
      type string {
        length "0..33";
      }
      description "End-of-download received from IM timestamp";
    }
    leaf eod-sent-imdr-time-stamp {
      xr:xr-xml-map "fib:EODSentIMDRTimeStamp";
      type string {
        length "0..33";
      }
      description "End-of-download send to IMDR timestamp";
    }
    leaf eod-sent-slc-time-stamp {
      xr:xr-xml-map "fib:EODSentSLCTimeStamp";
      type string {
        length "0..33";
      }
      description "End-of-download send to SLC timestamp";
    }
    leaf fis-issu-error-ts {
      xr:xr-xml-map "fib:fis_issu_error_ts";
      type uint64;
      description "ISSU error sent to ISSUMGR timetstamp";
    }

    list fis-proto-state {
      max-elements "3";
      description "IMDR state for the protocols";
      uses FIB-ISSU-PROTO-STATE;
    }
  }
}
