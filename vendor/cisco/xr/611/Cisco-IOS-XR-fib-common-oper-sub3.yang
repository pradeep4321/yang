submodule Cisco-IOS-XR-fib-common-oper-sub3 {

  belongs-to Cisco-IOS-XR-fib-common-oper {
    prefix Cisco-IOS-XR-fib-common-oper;
  }

  /*** LINKAGE (IMPORTS / INCLUDES) ***/

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR fib-common package operational data.

     Copyright (c) 2013-2016 by Cisco Systems, Inc.
     All rights reserved.";

  revision "2015-11-09" {
    description
      "IOS XR 6.0 revision.";
  }

  typedef Next-hop {
    type enumeration {
      enum tx {
        value 0;
        description "TX";
      }
      enum rx {
        value 1;
        description "RX";
      }
      enum special {
        value 2;
        description "Special";
      }
    }
    description "MPLS Forwarding Next Hop Type";
  }
  typedef Proto {
    type enumeration {
      enum ipv4 {
        value 0;
        description "IPv4";
      }
      enum ipv6 {
        value 1;
        description "IPv6";
      }
      enum mpls {
        value 2;
        description "MPLS";
      }
    }
    description "MPLS Forwarding Protocol Type";
  }

  grouping MPLS-LABEL-SECURITY-SUMMARY {
    description "MPLS LABEL SECURITY SUMMARY";
    leaf rpf-drops {
      xr:xr-xml-map "mpls_fwd:RPFDrops";
      type uint64;
      description "RPF drops";
    }
    leaf multi-label-drops {
      xr:xr-xml-map "mpls_fwd:MultiLabelDrops";
      type uint64;
      description "Multi-label drops";
    }
  }

  grouping MPLS-LABEL-SECURITY-INTF {
    description "MPLS LABEL SECURITY INTF";
    leaf rpf-enabled {
      xr:xr-xml-map "mpls_fwd:RPFEnabled";
      type boolean;
      description "RPF is enabled on interface";
    }
    leaf rpf-supported {
      xr:xr-xml-map "mpls_fwd:RPFSupported";
      type boolean;
      description "RPF stats supported per interface";
    }
    leaf mld-enabled {
      xr:xr-xml-map "mpls_fwd:MLDEnabled";
      type boolean;
      description "Multi-label drop is enabled on interface";
    }
    leaf mld-supported {
      xr:xr-xml-map "mpls_fwd:MLDSupported";
      type boolean;
      description
        "Multi-label drop counters are supported per
        interface";
    }
    leaf rpf-drops {
      xr:xr-xml-map "mpls_fwd:RPFDrops";
      type uint64;
      description "RPF drops";
    }
    leaf multi-label-drops {
      xr:xr-xml-map "mpls_fwd:MultiLabelDrops";
      type uint64;
      description "Multi-label drops";
    }
    leaf rpfifh {
      xr:xr-xml-map "mpls_fwd:RPFIFH";
      type xr:Interface-name;
      description "RPF interface handle";
    }
  }

  grouping MPLS-MCAST-INFO {
    description "Information for mpls multicast entries";
    leaf multicast-mol-base-flags {
      xr:xr-xml-map "mpls_fwd:MulticastMOLBaseFlags";
      type uint32;
      description "MOL base flags";
    }
    leaf multicast-mol-flags {
      xr:xr-xml-map "mpls_fwd:MulticastMOLFlags";
      type uint16;
      description "MOL flags";
    }
    leaf multicast-mol-referance-count {
      xr:xr-xml-map "mpls_fwd:MulticastMOLReferanceCount";
      type uint16;
      description "MOL refcount";
    }
    leaf multicast-tunnel-interface-handler {
      xr:xr-xml-map "mpls_fwd:MulticastTunnelInterfaceHandler";
      type xr:Interface-name;
      description "multicast mpls tunnel";
    }
    leaf multicast-tunnel-id {
      xr:xr-xml-map "mpls_fwd:MulticastTunnelID";
      type uint32;
      description
        "multicast mpls P2MP-TE tunnel id or MLDP Tunnel
        LSMID on all nodes";
    }
    leaf multicast-tunnel-next-hop-information {
      xr:xr-xml-map "mpls_fwd:MulticastTunnelNextHopInformation";
      type uint32;
      description "multicast nhinfo for p2mp TE Head";
    }
    leaf multicast-tunnel-lspvif {
      xr:xr-xml-map "mpls_fwd:MulticastTunnelLSPVIF";
      type uint32;
      description "multicast LSPVIF for MLDP Tunnels";
    }
    leaf multicast-mpls-output-paths {
      xr:xr-xml-map "mpls_fwd:MulticastMPLSOutputPaths";
      type uint16;
      description "num multicast mpls output paths ";
    }
    leaf multicast-mpls-protocol-output-paths {
      xr:xr-xml-map "mpls_fwd:MulticastMPLSProtocolOutputPaths";
      type uint16;
      description "num multicast mpls prot output paths ";
    }
    leaf multicast-mpls-local-output-paths {
      xr:xr-xml-map "mpls_fwd:MulticastMPLSLocalOutputPaths";
      type uint16;
      description "num multicast mpls local output paths";
    }
    leaf multicast-rpf-id {
      xr:xr-xml-map "mpls_fwd:MulticastRPF_ID";
      type uint32;
      description "The multicast RPF-ID ";
    }
    leaf multicast-encap-id {
      xr:xr-xml-map "mpls_fwd:MulticastEncap_ID";
      type uint32;
      description "The multicast ENCAP-ID ";
    }
    leaf multicast-platform-data-length {
      xr:xr-xml-map "mpls_fwd:MulticastPlatformDataLength";
      type uint8;
      description "The multicast platform data len";
    }
    leaf multicast-platform-data {
      xr:xr-xml-map "mpls_fwd:MulticastPlatformData";
      type yang:hex-string;
      description "The multicast platform data";
    }
  }

  grouping MPLS-LDI-INFO {
    description
      "Detailed load sharing information for mpls table
      entries";
    leaf ldi-hardware-information {
      xr:xr-xml-map "mpls_fwd:LDIHardwareInformation";
      type yang:hex-string;
      description "Hardware info";
    }
  }

  grouping MPLS-FWD-INFO {
    description "MPLS FWD INFO";
    leaf l3-mtu {
      xr:xr-xml-map "mpls_fwd:L3_MTU";
      type uint32;
      description "L3 MTU";
    }
    leaf total-encapsulation-size {
      xr:xr-xml-map "mpls_fwd:TotalEncapsulationSize";
      type uint32;
      description "Total encapsulation size: L2 + MPLS";
    }
    leaf mac-size {
      xr:xr-xml-map "mpls_fwd:MACSize";
      type uint32;
      description "Length of L2 encapsulation";
    }
    leaf transmit-number-of-packets-switched {
      xr:xr-xml-map "mpls_fwd:TransmitNumberOfPacketsSwitched";
      type uint64;
      description "Number of packets switched";
    }
    leaf transmit-number-of-bytes-switched {
      xr:xr-xml-map "mpls_fwd:TransmitNumberOfBytesSwitched";
      type uint64;
      units "byte";
      description "Number of Bytes switched";
    }
    leaf status {
      xr:xr-xml-map "mpls_fwd:Status";
      type int32;
      description "Status";
    }
    leaf next-hop-interface {
      xr:xr-xml-map "mpls_fwd:NextHopInterface";
      type xr:Interface-name;
      description "Next hop interface";
    }
    leaf next-hop-protocol {
      xr:xr-xml-map "mpls_fwd:NextHopProtocol";
      type Proto;
      description "The address family (V4/V6) ";
    }
    leaf next-hop-string {
      xr:xr-xml-map "mpls_fwd:NextHopString";
      type yang:hex-string;
      description "Next hop address in string format";
    }
    leaf-list label-stack {
      xr:xr-xml-map "mpls_fwd:LabelStack";
      type uint32;
      description "Label stack";
    }
  }

  grouping MPLS-ADJ-INFO {
    description "MPLS ADJ INFO";

    list mpls-adj-info {
      description "mpls adj info";

      container label-information-detail {
        description "Detail label info";
        uses MPLS-FWD-INFO;
      }
      leaf label-information-type {
        type uint32;
        description "Label-Info type";
      }
      leaf local-label {
        type uint32;
        description "Local label";
      }
      leaf outgoing-label {
        type uint32;
        description "Outgoing label";
      }
      leaf mpls-adjacency-flags {
        type uint32;
        description "MPLS Adjacency flags";
      }
      leaf tunnel-id-present {
        type boolean;
        description "Tunnel id present?";
      }
      leaf outgoing-interface {
        type xr:Interface-name;
        description "Outgoing interface";
      }
      leaf outgoing-physical-interface {
        type xr:Interface-name;
        description "Outgoing Physical Interface";
      }
      leaf tunnel-interface {
        type xr:Interface-name;
        description "Tunnel Interface";
      }
      leaf label-information-path-index {
        type uint32;
        description "LabelInformationPathIndex";
      }
      leaf label-information-next-hop-type {
        type Next-hop;
        description "NHinfo Type";
      }
      leaf label-information-next-hop-protocol {
        type Proto;
        description "The address family (v4/v6) ";
      }
      leaf tx-bytes {
        type uint64;
        units "byte";
        description "Bytes transmitted per LSP";
      }
      leaf tx-packets {
        type uint64;
        description "Packets transmitted per LSP";
      }
      leaf outgoing-interface-string {
        type string {
          length "0..64";
        }
        description "Output Interface in string format";
      }
      leaf outgoing-label-string {
        type string {
          length "0..64";
        }
        description "Output Label in string format";
      }
      leaf prefix-or-id {
        type string {
          length "0..64";
        }
        description "Prefix Or ID";
      }
      leaf label-information-next-hop-string {
        type string {
          length "0..60";
        }
        description "Next hop address in string format";
      }
      leaf label-information-route-version {
        type uint64;
        description "The version of the route";
      }
      leaf label-information-time-in-milli-seconds {
        type uint64;
        description "The time of last update in msec";
      }
    }
  }

  grouping MPLS-SH-LEAF {
    description "Information about label leaf";

    container label-information {
      description "Label-info in FIB leaf";
      uses MPLS-ADJ-INFO;
    }

    container ldi-information {
      description "LDI-info in FIB leaf";
      uses MPLS-LDI-INFO;
    }

    container multicast-information {
      description "The multicast info";
      uses MPLS-MCAST-INFO;
    }
    leaf leaf-local-label {
      xr:xr-xml-map "mpls_fwd:LeafLocalLabel";
      type uint32;
      description "Local label";
    }
    leaf eos-bit {
      xr:xr-xml-map "mpls_fwd:EOSBit";
      type uint32;
      description "EOS bit";
    }
    leaf hardware-information {
      xr:xr-xml-map "mpls_fwd:HardwareInformation";
      type yang:hex-string;
      description "Hardware info";
    }
    leaf leaf-referance-count {
      xr:xr-xml-map "mpls_fwd:LeafReferanceCount";
      type uint32;
      description "Number of references to the leaf";
    }
    leaf leaf-flags {
      xr:xr-xml-map "mpls_fwd:LeafFlags";
      type uint32;
      description "The leaf flags";
    }
    leaf path-list-referance-count {
      xr:xr-xml-map "mpls_fwd:PathListReferanceCount";
      type uint32;
      description "Number of references to the pathlist";
    }
    leaf path-list-flags {
      xr:xr-xml-map "mpls_fwd:PathListFlags";
      type uint32;
      description "The pathlist flags";
    }
    leaf ldi-referance-count {
      xr:xr-xml-map "mpls_fwd:LDIReferanceCount";
      type uint32;
      description "Number of references to the LDI";
    }
    leaf ldi-flags {
      xr:xr-xml-map "mpls_fwd:LDIFlags";
      type uint32;
      description "The LDI flags";
    }
    leaf ldi-type {
      xr:xr-xml-map "mpls_fwd:LDIType";
      type uint32;
      description "The LDI type";
    }
    leaf ldi-pointer {
      xr:xr-xml-map "mpls_fwd:LDIPointer";
      type uint32;
      description "The pointer to the LDI";
    }
    leaf lw-ldi-type {
      xr:xr-xml-map "mpls_fwd:LW_LDIType";
      type uint32;
      description "The LW-LDI type";
    }
    leaf lw-ldi-pointer {
      xr:xr-xml-map "mpls_fwd:LW_LDIPointer";
      type uint32;
      description "The pointer to the LW-LDI";
    }
    leaf lw-ldi-refernace-count {
      xr:xr-xml-map "mpls_fwd:LW_LDIRefernaceCount";
      type uint32;
      description "The LW-LDI refcounter";
    }
    leaf lw-shared-ldi-pointer {
      xr:xr-xml-map "mpls_fwd:LWSharedLDIPointer";
      type uint32;
      description "The pointer to the shared LDI in LW-LDI";
    }
    leaf lspa-flags {
      xr:xr-xml-map "mpls_fwd:LSPAFlags";
      type uint32;
      description "The LSPA flags";
    }
    leaf afi-table-id {
      xr:xr-xml-map "mpls_fwd:AFITableID";
      type uint32;
      description "The AFI table ID";
    }
    leaf multicast-label {
      xr:xr-xml-map "mpls_fwd:MulticastLabel";
      type boolean;
      description "The unicast or multicast label";
    }
    leaf leaf-time-in-milli-seconds {
      xr:xr-xml-map "mpls_fwd:LeafTimeInMilliSeconds";
      type uint64;
      description "The time of last update in msec";
    }
  }

  grouping MPLS-FWDING-SUMMARY {
    description "MPLS FWDING SUMMARY";
    leaf ipv4-imposition-entries {
      xr:xr-xml-map "mpls_fwd:IPv4ImpositionEntries";
      type uint32;
      description "Number of IPv4 imposition entries";
    }
    leaf reserved-label-entries {
      xr:xr-xml-map "mpls_fwd:ReservedLabelEntries";
      type uint32;
      description "Number of reserved label entries";
    }
    leaf label-switched-entries {
      xr:xr-xml-map "mpls_fwd:LabelSwitchedEntries";
      type uint32;
      description "Number of label swap/disposition entries";
    }
    leaf deleted-stale-entries {
      xr:xr-xml-map "mpls_fwd:DeletedStaleEntries";
      type uint32;
      description "Number of delete stale label entries";
    }
    leaf te-head-entries {
      xr:xr-xml-map "mpls_fwd:TEHeadEntries";
      type uint32;
      description "Number of TE tunnel head imposition entries";
    }
    leaf te-frr-head-entries {
      xr:xr-xml-map "mpls_fwd:TE_FRRHeadEntries";
      type uint32;
      description "Number of TE FRR tunnel head imposition entries";
    }
    leaf te-frr-interface-entries {
      xr:xr-xml-map "mpls_fwd:TE_FRRInterfaceEntries";
      type uint32;
      description "Number of TE FRR protected interface entries";
    }
    leaf te-frr-next-hop-entries {
      xr:xr-xml-map "mpls_fwd:TE_FRRNextHopEntries";
      type uint32;
      description "Number of TE FRR protected next-hop entries";
    }
    leaf te-mid-points-entries {
      xr:xr-xml-map "mpls_fwd:TEMidPointsEntries";
      type uint32;
      description "Number of TE MidPoints forwarding entries";
    }
    leaf te-frr-mid-points-entries {
      xr:xr-xml-map "mpls_fwd:TE_FRRMidPointsEntries";
      type uint32;
      description "Number of TE FRR MidPoints forwarding entries";
    }
    leaf te-internal-entries {
      xr:xr-xml-map "mpls_fwd:TEInternalEntries";
      type uint32;
      description "Number of TE internal forwarding entries";
    }
    leaf te-frr-internal-entries {
      xr:xr-xml-map "mpls_fwd:TE_FRRInternalEntries";
      type uint32;
      description "Number of TE internal forwarding entries";
    }
    leaf total-forwarding-updates {
      xr:xr-xml-map "mpls_fwd:TotalForwardingUpdates";
      type uint32;
      description "Total forwarding updates from LSD to LFDs";
    }
    leaf total-forwarding-update-messages {
      xr:xr-xml-map "mpls_fwd:TotalForwardingUpdateMessages";
      type uint32;
      description
        "Total forwarding update messages from LSD to
        LFDs";
    }
    leaf total-p2mp-forwarding-updates {
      xr:xr-xml-map "mpls_fwd:TotalP2MPForwardingUpdates";
      type uint32;
      description "Total forwarding updates from MRIB to LFDs";
    }
    leaf total-p2mp-forwarding-added-or-modify-messages {
      xr:xr-xml-map "mpls_fwd:TotalP2MPForwardingAddedOrModifyMessa"+
        "ges";
      type uint32;
      description
        "Total p2mp forwarding add/modify messages from
        MRIB to LFDs";
    }
    leaf total-p2mp-forwarding-delete-messages {
      xr:xr-xml-map "mpls_fwd:TotalP2MPForwardingDeleteMessages";
      type uint32;
      description
        "Total p2mp forwarding del messages from MRIB to
        LFDs";
    }
    leaf total-p2mp-forwarding-drop-messages {
      xr:xr-xml-map "mpls_fwd:TotalP2MPForwardingDropMessages";
      type uint32;
      description
        "Total p2mp forwarding messages dropped from MRIB
        to LFDs";
    }
    leaf total-p2mp-iir-forwarding-drop-messages {
      xr:xr-xml-map "mpls_fwd:TotalP2MP_IIRForwardingDropMessages";
      type uint32;
      description
        "Total IIR triggered p2mp forwarding MRIB
        messages dropped";
    }
    leaf lowest-label {
      xr:xr-xml-map "mpls_fwd:LowestLabel";
      type uint32;
      description "Lowest label in use";
    }
    leaf highest-label {
      xr:xr-xml-map "mpls_fwd:HighestLabel";
      type uint32;
      description "Highest Label in use";
    }
    leaf ignore-protect {
      xr:xr-xml-map "mpls_fwd:IgnoreProtect";
      type uint32;
      description "Number of TE tunnels treated as non-protected";
    }
    leaf mte-head-entries {
      xr:xr-xml-map "mpls_fwd:MTEHeadEntries";
      type uint32;
      description "Number of MTE tunnel head entries";
    }
    leaf mte-ll-entries {
      xr:xr-xml-map "mpls_fwd:MTE_LLEntries";
      type uint32;
      description "Number of MTE local entries";
    }
    leaf mte-midpoint-entries {
      xr:xr-xml-map "mpls_fwd:MTEMidpointEntries";
      type uint32;
      description "Number of MTE midpoint entries";
    }
    leaf global-dropped-packets {
      xr:xr-xml-map "mpls_fwd:GlobalDroppedPackets";
      type uint64;
      description "Number of global FIB packets dropped";
    }
    leaf global-fragmented-packets {
      xr:xr-xml-map "mpls_fwd:GlobalFragmentedPackets";
      type uint64;
      description "Number of global FIB packets fragmented";
    }
    leaf global-failed-lookups {
      xr:xr-xml-map "mpls_fwd:GlobalFailedLookups";
      type uint64;
      description "Number of global failed lookups";
    }
    leaf lrpf-entries {
      xr:xr-xml-map "mpls_fwd:LRPFEntries";
      type uint32;
      description "Number of labels with RPF";
    }
  }
}
