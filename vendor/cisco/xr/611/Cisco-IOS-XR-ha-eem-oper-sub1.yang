submodule Cisco-IOS-XR-ha-eem-oper-sub1 {

  belongs-to Cisco-IOS-XR-ha-eem-oper {
    prefix Cisco-IOS-XR-ha-eem-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ha-eem package operational data.

     Copyright (c) 2013-2016 by Cisco Systems, Inc.
     All rights reserved.";

  revision "2015-01-07" {
    description
      "IOS XR 5.3.1 revision.";
  }


  grouping PROCESS-CPU-UTIL {
    description "Process CPU utilization information";
    leaf process-name {
      xr:xr-xml-map "fh_fd_wdsysmon_edm:ProcessName";
      type string;
      description "Process name";
    }
    leaf process-id {
      xr:xr-xml-map "fh_fd_wdsysmon_edm:ProcessID";
      type uint32;
      description "Process ID";
    }
    leaf process-cpu-one-minute {
      xr:xr-xml-map "fh_fd_wdsysmon_edm:ProcessCPUOneMinute";
      type uint32;
      units "percentage";
      description
        "Process CPU utilization in percent for past 1
        minute";
    }
    leaf process-cpu-five-minute {
      xr:xr-xml-map "fh_fd_wdsysmon_edm:ProcessCPUFiveMinute";
      type uint32;
      units "percentage";
      description
        "Process CPU utilization in percent for past 5
        minute";
    }
    leaf process-cpu-fifteen-minute {
      xr:xr-xml-map "fh_fd_wdsysmon_edm:ProcessCPUFifteenMinute";
      type uint32;
      units "percentage";
      description
        "Process CPU utilization in percent for past 15
        minute";
    }
  }

  grouping NODE-CPU-UTIL {
    description "Node CPU utilization information";
    leaf total-cpu-one-minute {
      xr:xr-xml-map "fh_fd_wdsysmon_edm:TotalCPUOneMinute";
      type uint32;
      description "Total CPU utilization in past 1 minute";
    }
    leaf total-cpu-five-minute {
      xr:xr-xml-map "fh_fd_wdsysmon_edm:TotalCPUFiveMinute";
      type uint32;
      description "Total CPU utilization in past 5 minute";
    }
    leaf total-cpu-fifteen-minute {
      xr:xr-xml-map "fh_fd_wdsysmon_edm:TotalCPUFifteenMinute";
      type uint32;
      description "Total CPU utilization in past 15 minute";
    }

    list process-cpu {
      description "Per process CPU utilization";
      uses PROCESS-CPU-UTIL;
    }
  }
}
