module Cisco-IOS-XR-ip-iep-oper {

  /*** NAMESPACE / PREFIX DEFINITION ***/

  namespace "http://cisco.com/ns/yang/Cisco-IOS-XR-ip-iep-oper";


  prefix "ip-iep-oper";

  /*** LINKAGE (IMPORTS / INCLUDES) ***/

  import Cisco-IOS-XR-types { prefix "xr"; }

  include Cisco-IOS-XR-ip-iep-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-iep package operational data.

     This module contains definitions
     for the following management objects:
       explicit-paths: Configured IP explicit paths

     Copyright (c) 2013-2016 by Cisco Systems, Inc.
     All rights reserved.";

  revision "2015-11-09" {
    description
      "IOS XR 6.0 revision.";
  }


  container explicit-paths {
    xr:xr-xml-map "ip_iep_oper:ExplicitPaths";
    config false;
    description "Configured IP explicit paths";

    container identifiers {
      xr:xr-xml-map "ip_iep_oper:IdentifierTable";
      description "List of configured IP explicit path identifiers";

      list identifier {
        xr:xr-xml-map "ip_iep_oper:Identifier";
        key "identifier-id";
        description
          "IP explicit path configured for a particular
          identifier";
        leaf identifier-id {
          xr:xr-xml-map "ip_iep_oper:IdentifierID";
          type int32;
          description "Identifier ID";
        }
        uses IEP-EXPLICIT-PATH;
      }
    }

    container names {
      xr:xr-xml-map "ip_iep_oper:NameTable";
      description "List of configured IP explicit path names";

      list name {
        xr:xr-xml-map "ip_iep_oper:Name";
        key "path-name";
        description
          "IP explicit path configured for a particular
          path name";
        leaf path-name {
          xr:xr-xml-map "ip_iep_oper:PathName";
          type xr:Cisco-ios-xr-string;
          description "Path name";
        }
        uses IEP-EXPLICIT-PATH;
      }
    }
  }
}
