module Cisco-IOS-XR-ip-rib-ipv4-oper {

  /*** NAMESPACE / PREFIX DEFINITION ***/

  namespace "http://cisco.com/ns/yang/Cisco-IOS-XR-ip-rib-ipv4-oper";


  prefix "ip-rib-ipv4-oper";

  /*** LINKAGE (IMPORTS / INCLUDES) ***/

  import ietf-inet-types { prefix "inet"; }

  import Cisco-IOS-XR-types { prefix "xr"; }

  include Cisco-IOS-XR-ip-rib-ipv4-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-rib-ipv4 package operational data.

     This module contains definitions
     for the following management objects:
       rib-stdby: RIB standby node operational data
       rib: rib

     Copyright (c) 2013-2016 by Cisco Systems, Inc.
     All rights reserved.";

  revision "2015-11-09" {
    description
      "IOS XR 6.0 revision.";
  }

  typedef Rib-saf-name {
    type string {
      pattern "(Unicast)";
    }
    description
      "Unicast:   Comment: Ucast string for <safi_name>;
      Multicast: Comment: Mcast string for <safi_name>";
  }
  typedef Rib-af-name {
    type string {
      pattern "(IPv4)";
    }
    description
      "IPv4: Comment: v4 string for <afi_name>;         
      IPv6: Comment: v6 string for <afi_name>";
  }

  grouping VRF-TABLE {
    description "Common node of rib, rib-stdby";

    container vrfs {
      xr:xr-xml-map "rib_oper:VRFTable";
      description "VRF table";

      list vrf {
        xr:xr-xml-map "rib_oper:VRF";
        key "vrf-name";
        description "Specific VRF";

        container afs {
          xr:xr-xml-map "rib_oper:AFTable";
          description "Address Family (AF) table";

          list af {
            xr:xr-xml-map "rib_oper:AF";
            key "af-name";
            description "Specific AF information";

            container safs {
              xr:xr-xml-map "rib_oper:SAFTable";
              description "Subsequent Address Family (SAF) table";

              list saf {
                xr:xr-xml-map "rib_oper:SAF";
                key "saf-name";
                description "Specific SAF information";

                container ip-rib-route-table-names {
                  xr:xr-xml-map "rib_oper:IP_RIBRouteTable";
                  description "Global container of routes";

                  list ip-rib-route-table-name {
                    xr:xr-xml-map "rib_oper:IP_RIBRouteTableName";
                    key "route-table-name";
                    description
                      "IP RIB Route table name for a topology";

                    container backup-routes {
                      xr:xr-xml-map "rib_oper:BackupKW";
                      description "Backup";

                      list backup-route {
                        xr:xr-xml-map "rib_oper:BackupRoute";
                        description
                          "Route information for a specific backup
                          address ";
                        leaf address {
                          xr:xr-xml-map "rib_oper:Address";
                          type inet:ipv4-address-no-zone;
                          description "Network Address";
                        }
                        leaf prefix-length {
                          xr:xr-xml-map "rib_oper:PrefixLength";
                          type xr:Ipv4-prefix-length;
                          description "Prefix Length";
                        }
                        uses IPV4-RIB-EDM-ROUTE;
                      }
                    }

                    container routes {
                      xr:xr-xml-map "rib_oper:RouteTable";
                      description "Route information ";

                      list route {
                        xr:xr-xml-map "rib_oper:Route";
                        description
                          "Route information of a specific Network
                          Address ";
                        leaf address {
                          xr:xr-xml-map "rib_oper:Address";
                          type inet:ipv4-address-no-zone;
                          description "Network Address";
                        }
                        leaf prefix-length {
                          xr:xr-xml-map "rib_oper:PrefixLength";
                          type xr:Ipv4-prefix-length;
                          description "Prefix Length";
                        }
                        leaf next-hop-address {
                          xr:xr-xml-map "rib_oper:NextHopAddress";
                          type inet:ipv4-address-no-zone;
                          description "NextHop Address";
                        }
                        leaf interface-name {
                          xr:xr-xml-map "rib_oper:InterfaceName";
                          type xr:Interface-name;
                          description "Outgoing Interface";
                        }
                        uses IPV4-RIB-EDM-ROUTE;
                      }
                    }

                    container deleted-routes {
                      xr:xr-xml-map "rib_oper:DeletedKW";
                      description "Deleted";

                      list deleted-route {
                        xr:xr-xml-map "rib_oper:DeletedRoutes";
                        description
                          "Route information for a specific
                          deleted address ";
                        leaf address {
                          xr:xr-xml-map "rib_oper:Address";
                          type inet:ipv4-address-no-zone;
                          description "Network Address";
                        }
                        leaf prefix-length {
                          xr:xr-xml-map "rib_oper:PrefixLength";
                          type xr:Ipv4-prefix-length;
                          description "Prefix Length";
                        }
                        uses IPV4-RIB-EDM-ROUTE;
                      }
                    }

                    container destination-kw {
                      xr:xr-xml-map "rib_oper:DestinationKW";
                      description "Destination KW";

                      container dest-best-routes {
                        xr:xr-xml-map "rib_oper:DestBestKW";
                        description "Best Local";

                        list dest-best-route {
                          xr:xr-xml-map "rib_oper:DestBestRoute";
                          key "address";
                          description
                            "Best local route information for a
                            specific Address ";
                          leaf address {
                            xr:xr-xml-map "rib_oper:Address";
                            type inet:ipv4-address-no-zone;
                            description "Network Address";
                          }
                          uses IPV4-RIB-EDM-ROUTE;
                        }
                      }

                      container dest-q-routes {
                        xr:xr-xml-map "rib_oper:DestQ_KW";
                        description "Quarantine";

                        list dest-q-route {
                          xr:xr-xml-map "rib_oper:DestQ_Route";
                          description
                            "Route information of a specific Backup
                            Address ";
                          leaf address {
                            xr:xr-xml-map "rib_oper:Address";
                            type inet:ipv4-address-no-zone;
                            description "Network Address";
                          }
                          leaf prefix-length {
                            xr:xr-xml-map "rib_oper:PrefixLength";
                            type xr:Ipv4-prefix-length;
                            description "Prefix Length";
                          }
                          uses IPV4-RIB-EDM-ROUTE;
                        }
                      }

                      container dest-backup-routes {
                        xr:xr-xml-map "rib_oper:DestBackupKW";
                        description "Backup";

                        list dest-backup-route {
                          xr:xr-xml-map "rib_oper:DestBackupRoute";
                          description
                            "Route information of a specific Backup
                            Address ";
                          leaf address {
                            xr:xr-xml-map "rib_oper:Address";
                            type inet:ipv4-address-no-zone;
                            description "Network Address";
                          }
                          leaf prefix-length {
                            xr:xr-xml-map "rib_oper:PrefixLength";
                            type xr:Ipv4-prefix-length;
                            description "Prefix Length";
                          }
                          uses IPV4-RIB-EDM-ROUTE;
                        }
                      }

                      container dest-next-hop-routes {
                        xr:xr-xml-map "rib_oper:DestNextHopKW";
                        description "Resolving next hop";

                        list dest-next-hop-route {
                          xr:xr-xml-map "rib_oper:DestNextHopRoute";
                          key "address";
                          description
                            "Nexthop information for a specific
                            address";
                          leaf address {
                            xr:xr-xml-map "rib_oper:Address";
                            type inet:ipv4-address-no-zone;
                            description "Network Address";
                          }
                          uses IPV4-RIB-EDM-ROUTE;
                        }
                      }
                    }

                    container opaques {
                      xr:xr-xml-map "rib_oper:OpaquesByTable";
                      description "Opaque information ";

                      list opaque {
                        xr:xr-xml-map "rib_oper:Opaques";
                        description "Opaque item ";
                        leaf opaque-clientid {
                          xr:xr-xml-map "rib_oper:opaque_clientid";
                          type int32;
                          description "Opaque Client ID";
                        }
                        leaf opaque-protoid {
                          xr:xr-xml-map "rib_oper:opaque_protoid";
                          type int32;
                          description "Opaque Proto ID";
                        }
                        leaf opaque-key-type {
                          xr:xr-xml-map "rib_oper:opaque_key_type";
                          type int32;
                          description "Opaque key type";
                        }
                        leaf opaque-key-size {
                          xr:xr-xml-map "rib_oper:opaque_key_size";
                          type int32;
                          description "Opaque key size";
                        }
                        leaf opaque-data-size {
                          xr:xr-xml-map "rib_oper:opaque_data_size";
                          type int32;
                          description "Opaque data size";
                        }
                        leaf opaque-string {
                          xr:xr-xml-map "rib_oper:opaque_string";
                          type xr:Cisco-ios-xr-string;
                          description "Opaque string";
                        }
                        uses RIB-EDM-OPAQUE-OBJ;
                      }
                    }

                    container protocol {
                      xr:xr-xml-map "rib_oper:Protocol";
                      description
                        "Contains the classification of routes by
                        protocol";

                      container mobile {
                        xr:xr-xml-map "rib_oper:Mobile";
                        description "Mobile Protocol";
                        uses NON-AS;
                      }

                      container subscriber {
                        xr:xr-xml-map "rib_oper:Subscriber";
                        description "Subscriber Protocol";
                        uses NON-AS;
                      }

                      container connected {
                        xr:xr-xml-map "rib_oper:Connected";
                        description "Connected Protocol";
                        uses NON-AS;
                      }

                      container dagr {
                        xr:xr-xml-map "rib_oper:DAGR";
                        description
                          "DAGR Protocol(Direct-Attached Gateway
                          Redundancy) Protocol";
                        uses NON-AS;
                      }

                      container rip {
                        xr:xr-xml-map "rib_oper:RIP";
                        description "RIP Protocol";
                        uses NON-AS;
                      }

                      container ospf {
                        xr:xr-xml-map "rib_oper:OSPF";
                        description "OSPF Protocol";
                        uses AS;
                      }

                      container static {
                        xr:xr-xml-map "rib_oper:Static";
                        description "Static Protocol";
                        uses NON-AS;
                      }

                      container rpl {
                        xr:xr-xml-map "rib_oper:RPL";
                        description "RPL Protocol";
                        uses AS;
                      }

                      container application {
                        xr:xr-xml-map "rib_oper:Application";
                        description "Application Protocol";
                        uses NON-AS;
                      }

                      container eigrp {
                        xr:xr-xml-map "rib_oper:EIGRP";
                        description "EIGRP Protocol";
                        uses AS;
                      }

                      container local {
                        xr:xr-xml-map "rib_oper:Local";
                        description "Local Protocol";

                        container smiap {
                          xr:xr-xml-map "rib_oper:SMIAP";
                          description "SMIAP";
                          uses PROTOCOL-ROUTE-TABLE;
                          uses INFORMATION;
                        }

                        container lspv {
                          xr:xr-xml-map "rib_oper:LSPV";
                          description
                            "LSPV(Label Switched Path Verification)
                            Protocol";
                          uses PROTOCOL-ROUTE-TABLE;
                          uses INFORMATION;
                        }
                        uses NON-AS;
                      }

                      container bgp {
                        xr:xr-xml-map "rib_oper:BGP";
                        description "BGP Protocol";
                        uses AS;
                      }

                      container isis {
                        xr:xr-xml-map "rib_oper:ISIS";
                        description "ISIS Protocol";
                        uses AS;
                      }
                    }

                    container q-routes {
                      xr:xr-xml-map "rib_oper:Q_KW";
                      description "Quarantine";

                      list q-route {
                        xr:xr-xml-map "rib_oper:Q_Route";
                        description
                          "Route information for a specific
                          quarantined address ";
                        leaf address {
                          xr:xr-xml-map "rib_oper:Address";
                          type inet:ipv4-address-no-zone;
                          description "Network Address";
                        }
                        leaf prefix-length {
                          xr:xr-xml-map "rib_oper:PrefixLength";
                          type xr:Ipv4-prefix-length;
                          description "Prefix Length";
                        }
                        uses IPV4-RIB-EDM-ROUTE;
                      }
                    }

                    container adverts {
                      xr:xr-xml-map "rib_oper:AdvertsList";
                      description "Route advertiser information ";

                      list advert {
                        xr:xr-xml-map "rib_oper:Adverts";
                        description
                          "Route information of a specific Network
                          Address ";
                        leaf address {
                          xr:xr-xml-map "rib_oper:Address";
                          type inet:ipv4-address-no-zone;
                          description "Network Address";
                        }
                        leaf prefix-length {
                          xr:xr-xml-map "rib_oper:PrefixLength";
                          type xr:Ipv4-prefix-length;
                          description "Prefix Length";
                        }
                        uses IPV4-RIB-EDM-ADVERT;
                      }
                    }
                    leaf route-table-name {
                      xr:xr-xml-map "rib_oper:RouteTableName";
                      type xr:Cisco-ios-xr-string;
                      description "Name of the route table";
                    }
                  }
                }
                leaf saf-name {
                  xr:xr-xml-map "rib_oper:SAFName";
                  type Rib-saf-name;
                  description "Name of the SAF";
                }
              }
            }
            leaf af-name {
              xr:xr-xml-map "rib_oper:AFName";
              type Rib-af-name;
              description "Name of the AF";
            }
          }
        }
        leaf vrf-name {
          xr:xr-xml-map "rib_oper:VRFName";
          type xr:Cisco-ios-xr-string;
          description "Name of the VRF";
        }
      }
    }
  }

  grouping AS {
    description "Common node of bgp, ospf, isis, eigrp, rpl";

    list as {
      xr:xr-xml-map "rib_oper:AS";
      key "as";
      description "Autonomous System of protocol";
      leaf as {
        xr:xr-xml-map "rib_oper:AS";
        type xr:Cisco-ios-xr-string;
        description "Autonomous system";
      }
      uses PROTOCOL-ROUTE-TABLE;
      uses INFORMATION;
    }
  }

  grouping INFORMATION {
    description "Common node of as, non-as, smiap, lspv";

    container information {
      xr:xr-xml-map "rib_oper:Information";
      description "Protocol related Information";
      uses IPV4-RIB-EDM-PROTO;
    }
  }

  grouping RIB-TABLE {
    description "Common node of rib, rib-stdby";

    container rib-table-ids {
      xr:xr-xml-map "rib_oper:RIBTable";
      description "RIB table";

      list rib-table-id {
        xr:xr-xml-map "rib_oper:RIBTableID";
        key "tableid";
        description "Specific Table";

        container summary-protos {
          xr:xr-xml-map "rib_oper:RIBTableSummary";
          description "RIB table summary";

          list summary-proto {
            xr:xr-xml-map "rib_oper:SummaryProto";
            key "protoid";
            description
              "Route summary information for a specific
              table/protocol ";
            leaf protoid {
              xr:xr-xml-map "rib_oper:protoid";
              type int32;
              description "Proto ID";
            }
            uses RIB-EDM-PROTO-ROUTE-SUMM-DETAIL;
          }
        }

        container rib-table-itf-hndls {
          xr:xr-xml-map "rib_oper:RIBTableItf";
          description "RIB table interface";

          list rib-table-itf-hndl {
            xr:xr-xml-map "rib_oper:RIBTableItfHndl";
            key "handle";
            description "Interface handle";
            leaf handle {
              xr:xr-xml-map "rib_oper:handle";
              type int32;
              description "Itf Handle";
            }

            list itf-route {
              xr:xr-xml-map "rib_oper:ItfRoutes";
              key "address";
              description
                "Route information for a specific
                table/interface ";
              leaf address {
                xr:xr-xml-map "rib_oper:Address";
                type inet:ipv4-address-no-zone;
                description "Network Address";
              }
              uses IPV4-RIB-EDM-ROUTE;
            }
          }
        }
        leaf tableid {
          xr:xr-xml-map "rib_oper:tableid";
          type xr:Hex-integer;
          description "Table ID";
        }
      }
    }
  }

  grouping NON-AS {
    description
      "Common node of local, connected, rip, static,
      subscriber, mobile, dagr, application";

    container non-as {
      xr:xr-xml-map "rib_oper:NonAS";
      description "Non Autonomous System of protocol";
      uses PROTOCOL-ROUTE-TABLE;
      uses INFORMATION;
    }
  }

  grouping PROTOCOL-ROUTE-TABLE {
    description "Common node of as, non-as, smiap, lspv";

    container protocol-routes {
      xr:xr-xml-map "rib_oper:ProtocolRouteTable";
      description "Protocol specific Route";

      list protocol-route {
        xr:xr-xml-map "rib_oper:ProtocolRoute";
        description
          " Route information of a specific Network
          Address ";
        leaf address {
          xr:xr-xml-map "rib_oper:Address";
          type inet:ipv4-address-no-zone;
          description "Network Address";
        }
        leaf prefix-length {
          xr:xr-xml-map "rib_oper:PrefixLength";
          type xr:Ipv4-prefix-length;
          description "Prefix Length";
        }
        uses IPV4-RIB-EDM-ROUTE;
      }
    }
  }

  container rib-stdby {
    xr:xr-xml-map "rib_oper:RIB-STDBY";
    config false;
    description "RIB standby node operational data";
    uses VRF-TABLE;
    uses RIB-TABLE;
  }

  container rib {
    xr:xr-xml-map "rib_oper:RIB";
    config false;
    description "rib";
    uses VRF-TABLE;
    uses RIB-TABLE;
  }
}
