submodule Cisco-IOS-XR-l2vpn-oper-sub4 {

  belongs-to Cisco-IOS-XR-l2vpn-oper {
    prefix Cisco-IOS-XR-l2vpn-oper;
  }

  /*** LINKAGE (IMPORTS / INCLUDES) ***/

  import ietf-inet-types { prefix "inet"; }

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR l2vpn package operational data.

     Copyright (c) 2013-2016 by Cisco Systems, Inc.
     All rights reserved.";

  revision "2015-11-09" {
    description
      "IOS XR 6.0 revision.";
  }

  typedef L2fib-g8032-aps-port-status {
    type enumeration {
      enum l2fib-aps-port-state-unknown {
        description "APS port state unknown";
      }
      enum l2fib-aps-port-state-unbound {
        description "APS port state unbound";
      }
      enum l2fib-aps-port-state-bound {
        description "APS port state bound";
      }
    }
    description "APS port status";
  }
  typedef L2fib-g8032-rpl {
    type enumeration {
      enum rpl-unknown {
        description "No RPL info";
      }
      enum port0-owner {
        description "Port 0 owner";
      }
      enum port0-neighbor {
        description "Port 0 neighbor";
      }
      enum port0-next-neighbor {
        description "Port 0 next neighbor";
      }
      enum port1-owner {
        description "Port 1 owner";
      }
      enum port1-neighbor {
        description "Port 1 neighbor";
      }
      enum port1-next-neighbor {
        description "Port 1 next neighbor";
      }
    }
    description "RPL types in g8032 ring";
  }
  typedef L2fib-l2tp-session {
    type enumeration {
      enum l2tpv3 {
        description "L2TPv3 session";
      }
      enum l2tpv2 {
        description "L2TPv2 session";
      }
    }
    description "L2TPv2 and L2TPv3 session type";
  }
  typedef L2fib-main-if-instance-state {
    type enumeration {
      enum forwarding {
        description "Forwarding state";
      }
      enum blocked {
        description "Blocked state";
      }
      enum mac-learning {
        description "Mac learning state";
      }
      enum nack {
        description "Nack state";
      }
      enum forwarning-not-useful {
        description "Forwarding not useful state";
      }
      enum blocked-not-useful {
        description "Blocked not useful state";
      }
      enum mac-learning-not-useful {
        description "Mac Learning not useful state";
      }
      enum blocked-data-only {
        description "Blocked data only state";
      }
      enum multicast-pe2ce-blocked {
        description "Multicast PE to CE blocked state";
      }
      enum multicast-blocked {
        description "Multicast blocked state";
      }
      enum port-state-unknown {
        description "Port state unknown";
      }
    }
    description "State of a main port instance";
  }
  typedef Mgmt-l2fib-bridge-mac-evpn-ctx {
    type enumeration {
      enum mgmt-l2fib-bridge-mac-evpn-ctx-none {
        description "mgmt l2fib bridge mac evpn ctx none";
      }
      enum mgmt-l2fib-bridge-mac-evpn-ctx-esi-id {
        description "mgmt l2fib bridge mac evpn ctx esi id";
      }
      enum mgmt-l2fib-bridge-mac-evpn-ctx-local-label {
        description "mgmt l2fib bridge mac evpn ctx local label";
      }
      enum mgmt-l2fib-bridge-mac-evpn-ctx-moi {
        description "mgmt l2fib bridge mac evpn ctx moi";
      }
    }
    description "Mgmt l2fib bridge mac evpn ctx";
  }
  typedef Mgmt-l2fib-stats-data {
    type enumeration {
      enum mgmt-l2fib-stats-type-unknown {
        description "mgmt l2fib stats type unknown";
      }
      enum mgmt-l2fib-stats-type-mcast {
        description "mgmt l2fib stats type mcast";
      }
    }
    description "Mgmt l2fib stats data";
  }
  typedef L2vpn-ptree {
    type enumeration {
      enum none {
        value 0;
        description "No ptree type";
      }
      enum rsvp-te {
        value 1;
        description "RSVP_TE ptree type";
      }
      enum mldp {
        value 2;
        description "MLDP ptree type";
      }
    }
    description "ptree type";
  }
  typedef L2fib-feature {
    type enumeration {
      enum l2fib-feature-dhcp-snooping {
        description "l2fib feature dhcp snooping";
      }
      enum l2fib-feature-igmp-snooping {
        description "l2fib feature igmp snooping";
      }
      enum l2fib-feature-mld-snooping {
        description "l2fib feature mld snooping";
      }
      enum l2fib-feature-max {
        description "l2fib feature max";
      }
    }
    description "L2fib feature";
  }
  typedef L2fib-storm-control-rate-unit {
    type enumeration {
      enum pps {
        description "Packets Per Second";
      }
      enum kb-ps {
        description "Kilobits Per Second";
      }
    }
    description "Storm Control Rate Unit Type";
  }
  typedef Mgmt-l2fib-mac-sec-action {
    type enumeration {
      enum not-set {
        value 0;
        description "MAC Secure Action Not Set";
      }
      enum restrict {
        value 1;
        description "MAC Secure Action Restrict";
      }
      enum none {
        value 2;
        description "MAC Secure Action None";
      }
      enum shutdown {
        value 3;
        description "MAC Secure Action Shutdown";
      }
    }
    description "Mgmt l2fib mac sec action";
  }
  typedef Mgmt-l2fib-mac-limit-notify {
    type enumeration {
      enum mgmt-l2fib-mac-limit-notify-none {
        description "mgmt l2fib mac limit notify none";
      }
      enum mgmt-l2fib-mac-limit-notify-syslog {
        description "mgmt l2fib mac limit notify syslog";
      }
      enum mgmt-l2fib-mac-limit-notify-trap {
        description "mgmt l2fib mac limit notify trap";
      }
      enum mgmt-l2fib-mac-limit-notify-both {
        description "mgmt l2fib mac limit notify both";
      }
    }
    description "Mgmt l2fib mac limit notify";
  }
  typedef Mgmt-l2fib-mac-limit-action {
    type enumeration {
      enum mgmt-l2fib-mac-limit-action-type-none {
        description "mgmt l2fib mac limit action type none";
      }
      enum mgmt-l2fib-mac-limit-action-type-flood {
        description "mgmt l2fib mac limit action type flood";
      }
      enum mgmt-l2fib-mac-limit-action-type-no-flood {
        description "mgmt l2fib mac limit action type no flood";
      }
      enum mgmt-l2fib-mac-limit-action-type-shutdown {
        description "mgmt l2fib mac limit action type shutdown";
      }
    }
    description "Mgmt l2fib mac limit action";
  }
  typedef L2fib-load-bal {
    type enumeration {
      enum flow-undef {
        description "Load Balance Flow Undefined";
      }
      enum src-dst-mac {
        description "Load Balance Flow src-dst-mac";
      }
      enum src-dst-ip {
        description "Load Balance Flow src-dst-ip";
      }
      enum vc {
        description "Load Balance VC based";
      }
    }
    description "L2fib load bal";
  }
  typedef L2fib-group-state {
    type enumeration {
      enum up {
        description "Group State Up";
      }
      enum down {
        description "Group State Down";
      }
    }
    description "group state";
  }
  typedef L2fib-pw-redundancy-role {
    type enumeration {
      enum primary {
        description "Primary pseudowire";
      }
      enum backup {
        description "Backup pseudowire";
      }
    }
    description "Pseudowire redundancy role";
  }
  typedef L2fib-pw-id {
    type enumeration {
      enum default {
        value 0;
        description "Default value - not set";
      }
      enum manual {
        value 1;
        description "Manual pseudowire ID";
      }
      enum vpls {
        value 2;
        description "VPLS pseudowire ID";
      }
      enum vpws {
        value 3;
        description "VPWS pseudowire ID";
      }
      enum vpls-ldp {
        value 4;
        description "VPLS with LDP signaling pseudowire ID";
      }
      enum l2fib-pw-id-type-pwr {
        value 5;
        description "PW-routing ID";
      }
      enum l2fib-pw-id-type-evpn {
        value 6;
        description "EVPN pseudowire ID";
      }
    }
    description "Pseudowire ID type";
  }
  typedef Mgmt-l2fib-bridge {
    type enumeration {
      enum mgmt-l2fib-bridge-type-default {
        value 0;
        description "mgmt l2fib bridge type default";
      }
      enum mgmt-l2fib-bridge-type-pbb-edge {
        value 1;
        description "mgmt l2fib bridge type pbb edge";
      }
      enum mgmt-l2fib-bridge-type-pbb-core {
        value 2;
        description "mgmt l2fib bridge type pbb core";
      }
    }
    description "Mgmt l2fib bridge";
  }
  typedef Mgmt-l2fib-data {
    type enumeration {
      enum mgmt-l2fib-data-type-min {
        description "mgmt l2fib data type min";
      }
      enum mgmt-l2fib-data-type-xcon {
        description "mgmt l2fib data type xcon";
      }
      enum mgmt-l2fib-data-type-ac {
        description "mgmt l2fib data type ac";
      }
      enum mgmt-l2fib-data-type-span {
        description "mgmt l2fib data type span";
      }
      enum mgmt-l2fib-data-type-atom {
        description "mgmt l2fib data type atom";
      }
      enum mgmt-l2fib-data-type-pbb {
        description "mgmt l2fib data type pbb";
      }
      enum mgmt-l2fib-data-type-vni {
        description "mgmt l2fib data type vni";
      }
      enum mgmt-l2fib-data-type-n-hop {
        description "mgmt l2fib data type n hop";
      }
      enum mgmt-l2fib-data-type-l2tp {
        description "mgmt l2fib data type l2tp";
      }
      enum mgmt-l2fib-data-type-l2tpv2 {
        description "mgmt l2fib data type l2tpv2";
      }
      enum mgmt-l2fib-data-type-bridge {
        description "mgmt l2fib data type bridge";
      }
      enum mgmt-l2fib-data-type-bridge-shg {
        description "mgmt l2fib data type bridge shg";
      }
      enum mgmt-l2fib-data-type-bridge-port {
        description "mgmt l2fib data type bridge port";
      }
      enum mgmt-l2fib-data-type-bridge-mac {
        description "mgmt l2fib data type bridge mac";
      }
      enum mgmt-l2fib-data-type-mcast-table {
        description "mgmt l2fib data type mcast table";
      }
      enum mgmt-l2fib-data-type-mcast-leaf {
        description "mgmt l2fib data type mcast leaf";
      }
      enum mgmt-l2fib-data-type-mcast-xid {
        description "mgmt l2fib data type mcast xid";
      }
      enum mgmt-l2fib-data-type-dhcp {
        description "mgmt l2fib data type dhcp";
      }
      enum mgmt-l2fib-data-type-l2tp-ipv6-ts {
        description "mgmt l2fib data type l2tp ipv6 ts";
      }
      enum mgmt-l2fib-data-type-pwhe-mp {
        description "mgmt l2fib data type pwhe mp";
      }
      enum mgmt-l2fib-data-type-evpn {
        description "mgmt l2fib data type evpn";
      }
      enum mgmt-l2fib-data-type-fxs {
        description "mgmt l2fib data type fxs";
      }
      enum mgmt-l2fib-data-type-max {
        description "mgmt l2fib data type max";
      }
    }
    description "Mgmt l2fib data";
  }
  typedef Mgmt-l2fib-switching {
    type enumeration {
      enum mgmt-l2fib-switching-type-unknown {
        description "mgmt l2fib switching type unknown";
      }
      enum mgmt-l2fib-switching-type-ac-ac {
        description "mgmt l2fib switching type ac ac";
      }
      enum mgmt-l2fib-switching-type-ac-atom {
        description "mgmt l2fib switching type ac atom";
      }
      enum mgmt-l2fib-switching-type-ac-vfi {
        description "mgmt l2fib switching type ac vfi";
      }
      enum mgmt-l2fib-switching-type-ac-l2tp {
        description "mgmt l2fib switching type ac l2tp";
      }
      enum mgmt-l2fib-switching-type-atom-atom {
        description "mgmt l2fib switching type atom atom";
      }
      enum mgmt-l2fib-switching-type-vfi-atom {
        description "mgmt l2fib switching type vfi atom";
      }
      enum mgmt-l2fib-switching-type-vfi-l2tp {
        description "mgmt l2fib switching type vfi l2tp";
      }
      enum mgmt-l2fib-switching-type-l2tp-atom {
        description "mgmt l2fib switching type l2tp atom";
      }
      enum mgmt-l2fib-switching-type-l2tp-l2tp {
        description "mgmt l2fib switching type l2tp l2tp";
      }
      enum mgmt-l2fib-switching-type-max {
        description "mgmt l2fib switching type max";
      }
    }
    description "Mgmt l2fib switching";
  }

  grouping L2FIB-DHCP-BINDING-SUMMARY-INFO {
    description "L2FIB DHCP binding summary info";

    container port {
      description "Union of Port information";
      uses L2FIB-DHCP-BIND-UN;
    }
    leaf bindings {
      xr:xr-xml-map "l2fib:Bindings";
      type uint32;
      description "DHCP binding count";
    }
  }

  grouping L2FIB-VTEP-INFO {
    description "L2FIB vtep info";
    leaf nve-if {
      xr:xr-xml-map "l2fib:NVE_IF";
      type xr:Interface-name;
      description "Parent NVE IF Handle";
    }
    leaf vn-iid {
      xr:xr-xml-map "l2fib:VNIid";
      type uint32;
      description "VNI ID";
    }
    leaf vte-pip {
      xr:xr-xml-map "l2fib:VTEPip";
      type inet:ipv4-address;
      description "Peer VTEP IP Address";
    }
  }

  grouping L2FIB-PWHE-MP-SUMMARY-INFO {
    description "L2VPN PWHE Main-port summary info";
    leaf total-count {
      xr:xr-xml-map "l2fib:TotalCount";
      type uint32;
      description "Number of PWHE Main-ports";
    }
  }

  grouping L2FIB-PWGROUP-SUMMARY-INFO {
    description "L2VPN PWGROUP summary info";
    leaf plat-grouping-supported {
      xr:xr-xml-map "l2fib:PlatGroupingSupported";
      type boolean;
      description "Platform supports Grouping";
    }
    leaf total-pw-groups {
      xr:xr-xml-map "l2fib:TotalPWGroups";
      type uint32;
      description "Total number of PWGROUP objects";
    }
    leaf pw-groups-down {
      xr:xr-xml-map "l2fib:PWGroupsDown";
      type uint32;
      description "Number of PWGROUP objects down";
    }
  }

  grouping L2FIB-PTREE-SUMMARY-INFO {
    description "L2VPN PTree summary info";
    leaf total-ptree-count {
      xr:xr-xml-map "l2fib:TotalPTreeCount";
      type uint32;
      description "Number of PTree objects";
    }
    leaf mldp-enabled-ptree-count {
      xr:xr-xml-map "l2fib:MLDPEnabledPTreeCount";
      type uint32;
      description "Number of MLDP enabled PTree objects";
    }
    leaf lmrib-mldp-ptree-count {
      xr:xr-xml-map "l2fib:LMRIB_MLDPPTreeCount";
      type uint32;
      description "Number of MLDP PTree Objects owned by LMRIB";
    }
    leaf rsvp-te-enabled-ptree-count {
      xr:xr-xml-map "l2fib:RSVP_TEEnabledPTreeCount";
      type uint32;
      description "Number of RSVP-TE enabled PTree objects";
    }
    leaf lmrib-rsvp-te-ptree-count {
      xr:xr-xml-map "l2fib:LMRIB_RSVP_TEPTreeCount";
      type uint32;
      description "Number of RSVP-TE PTree Objects owned by LMRIB";
    }
  }

  grouping L2FIB-GLOBAL-CFG-INFO {
    description "L2VPN Global Configuration";

    container base {
      description "Base Information";
      uses L2FIB-BASE-INFO;
    }
    leaf load-balance-type {
      xr:xr-xml-map "l2fib:LoadBalanceType";
      type L2fib-load-bal;
      description "Type of Load-Balancing";
    }
  }

  grouping L2FIB-EVPN-SUMMARY-INFO {
    description "L2VPN evpn summary info";
    leaf total-count {
      xr:xr-xml-map "l2fib:TotalCount";
      type uint32;
      description "Number of EVPN Multicast Replication lists";
    }
    leaf isid-count {
      xr:xr-xml-map "l2fib:ISIDCount";
      type uint32;
      description "Number of ISID leaves";
    }
    leaf default-count {
      xr:xr-xml-map "l2fib:DefaultCount";
      type uint32;
      description "Number of default leaves";
    }
  }

  grouping L2FIB-OBJ-QUEUES-SUMMARY {
    description "L2FIB OBJ QUEUES SUMMARY";
    leaf inline-cnt {
      xr:xr-xml-map "l2fib:InlineCnt";
      type uint32;
      description "number of objects in inline queue";
    }
    leaf retry-cnt {
      xr:xr-xml-map "l2fib:RetryCnt";
      type uint32;
      description "number of objects in retry queue";
    }
    leaf update-cnt {
      xr:xr-xml-map "l2fib:UpdateCnt";
      type uint32;
      description "number of objects in update queues";
    }
    leaf del-cnt {
      xr:xr-xml-map "l2fib:DelCnt";
      type uint32;
      description "number of objects in delete queues";
    }
  }

  grouping L2FIB-MAC-SUMMARY-INFO {
    description "L2FIB bridge mac summary info";
    leaf local-mac-count {
      xr:xr-xml-map "l2fib:LocalMACCount";
      type uint32;
      description "number of locally learnt macs";
    }
    leaf remote-mac-count {
      xr:xr-xml-map "l2fib:RemoteMACCount";
      type uint32;
      description "number of remotely learned macs";
    }
    leaf static-mac-count {
      xr:xr-xml-map "l2fib:StaticMACCount";
      type uint32;
      description "number of static macs";
    }
    leaf routed-mac-count {
      xr:xr-xml-map "l2fib:RoutedMACCount";
      type uint32;
      description "number of routed macs";
    }
    leaf mac-count {
      xr:xr-xml-map "l2fib:MACCount";
      type uint32;
      description "number of all macs";
    }
    leaf sbmac-count {
      xr:xr-xml-map "l2fib:SBMACCount";
      type uint32;
      description "number of Source BMACs";
    }
    leaf bmac-count {
      xr:xr-xml-map "l2fib:BMACCount";
      type uint32;
      description "number of BMACs";
    }
  }

  grouping L2FIB-BD-SUMMARY-INFO {
    description "L2VPN bridge-domain summary info";
    leaf bridge-domain-count {
      xr:xr-xml-map "l2fib:BridgeDomainCount";
      type uint32;
      description "Number of bridge-domains";
    }
    leaf bridge-domain-drop-count {
      xr:xr-xml-map "l2fib:BridgeDomainDropCount";
      type uint32;
      description "Number of bridge-domain updates dropped";
    }
    leaf bridge-domain-with-bvi-count {
      xr:xr-xml-map "l2fib:BridgeDomainWithBviCount";
      type uint32;
      description "Number of bridge-domains with BVI";
    }
    leaf bridge-domain-with-p2mp-enabled {
      xr:xr-xml-map "l2fib:BridgeDomainWithP2mpEnabled";
      type uint32;
      description "Number of bridge-domains with P2MP enabled";
    }
    leaf bridge-domain-with-pbbevpn-enabled {
      xr:xr-xml-map "l2fib:BridgeDomainWithPBBEVPNEnabled";
      type uint32;
      description "Number of bridge-domains with PBB EVPN enabled";
    }
    leaf bridge-domain-with-evpn-enabled {
      xr:xr-xml-map "l2fib:BridgeDomainWithEVPNEnabled";
      type uint32;
      description "Number of bridge-domains with EVPN enabled";
    }
  }

  grouping L2FIB-L2TP-DISP-SUMMARY-INFO {
    description "L2TP disposition session object summary";
    leaf l2tp-disposition-session-count {
      xr:xr-xml-map "l2fib:L2TPDispositionSessionCount";
      type uint32;
      description "number of l2tp disposition session objects";
    }
    leaf bound-l2tp-disposition-session-count {
      xr:xr-xml-map "l2fib:BoundL2TPDispositionSessionCount";
      type uint32;
      description "number of bound l2tp dispostion objects";
    }
    leaf unbound-l2tp-disposition-session-count {
      xr:xr-xml-map "l2fib:UnboundL2TPDispositionSessionCount";
      type uint32;
      description "number of unbound l2tp disposition objects";
    }
  }

  grouping L2FIB-NH-SUMMARY-INFO2 {
    description "Specific nhop summary";
    leaf next-hop-count {
      xr:xr-xml-map "l2fib:NextHopCount";
      type uint32;
      description "total number of nhops";
    }
    leaf bound-next-hop-count {
      xr:xr-xml-map "l2fib:BoundNextHopCount";
      type uint32;
      description "number of bound nhops";
    }
    leaf unbound-next-hop-count {
      xr:xr-xml-map "l2fib:UnboundNextHopCount";
      type uint32;
      description "number of unbound nhops";
    }
    leaf next-hop-pending-registration-count {
      xr:xr-xml-map "l2fib:NextHopPendingRegistrationCount";
      type uint32;
      description "number of nhops pending registration with fib ";
    }
  }

  grouping L2FIB-NH-SUMMARY-INFO {
    description "nhop db summary";

    container mpls {
      description "MPLS nexthop summary";
      uses L2FIB-NH-SUMMARY-INFO2;
    }

    container l2tp {
      description "L2TP nexthop summary";
      uses L2FIB-NH-SUMMARY-INFO2;
    }

    container lsm {
      description "LSM nexthop summary";
      uses L2FIB-NH-SUMMARY-INFO2;
    }

    container p2mp-tunnels {
      description "P2MPtun nexthop summary";
      uses L2FIB-NH-SUMMARY-INFO2;
    }
  }

  grouping L2FIB-XC-SUMMARY-INFO {
    description "xconnect db summary";
    leaf xconnect-count {
      xr:xr-xml-map "l2fib:XconnectCount";
      type uint32;
      description "total number of entries";
    }
    leaf xconnect-up-count {
      xr:xr-xml-map "l2fib:XconnectUpCount";
      type uint32;
      description "number of up entries";
    }
    leaf xconnect-down-count {
      xr:xr-xml-map "l2fib:XconnectDownCount";
      type uint32;
      description "number of down entries";
    }
    leaf ac-to-pw-count-mpls {
      xr:xr-xml-map "l2fib:ACToPWCountMPLS";
      type uint32;
      description "number of ac->pw-mpls entries";
    }
    leaf ac-to-pw-count-l2tp {
      xr:xr-xml-map "l2fib:ACToPWCountL2TP";
      type uint32;
      description "number of ac->pw-l2tp entries";
    }
    leaf ac-to-pw-count-l2tp-ip-v6 {
      xr:xr-xml-map "l2fib:ACToPWCountL2TPIpV6";
      type uint32;
      description "number of ac->pw-l2tp-ipv6 entries";
    }
    leaf ac-to-pw-count-l2tpv2 {
      xr:xr-xml-map "l2fib:ACToPWCountL2TPV2";
      type uint32;
      description "number of ac->pw-l2tpv2 entries";
    }
    leaf ac-to-ac-count {
      xr:xr-xml-map "l2fib:ACToACCount";
      type uint32;
      description "number of ac->ac entries";
    }
    leaf ac-to-unknown-count {
      xr:xr-xml-map "l2fib:ACToUnknownCount";
      type uint32;
      description "number of ac->unknown type entries";
    }
    leaf mon-sess-to-pw-count {
      xr:xr-xml-map "l2fib:MonSessToPWCount";
      type uint32;
      description "number of monitor_session->pw entries";
    }
    leaf mon-sess-to-unknown-count {
      xr:xr-xml-map "l2fib:MonSessToUnknownCount";
      type uint32;
      description "number of monitor_session->unknown type entries";
    }
    leaf ac-to-bp-count {
      xr:xr-xml-map "l2fib:ACToBPCount";
      type uint32;
      description "number of ac->bp entries";
    }
    leaf pw-to-bp-count {
      xr:xr-xml-map "l2fib:PWToBPCount";
      type uint32;
      description "number of pw->bp entries";
    }
    leaf pw-to-unknown-count {
      xr:xr-xml-map "l2fib:PWToUnknownCount";
      type uint32;
      description "number of pw->unknown type entries";
    }
    leaf pbb-to-bp-count {
      xr:xr-xml-map "l2fib:PBBToBPCount";
      type uint32;
      description "number of pbb->bp entries";
    }
    leaf pbb-to-unknown-count {
      xr:xr-xml-map "l2fib:PBBToUnknownCount";
      type uint32;
      description "number of pbb->unknown type entries";
    }
    leaf vni-to-bp-count {
      xr:xr-xml-map "l2fib:VNIToBPCount";
      type uint32;
      description "number of vni->bp 	     entries";
    }
    leaf vni-to-unknown-count {
      xr:xr-xml-map "l2fib:VNIToUnknownCount";
      type uint32;
      description "number of vni->unknown type entries";
    }
    leaf evpn-to-bp-count {
      xr:xr-xml-map "l2fib:EVPNToBPCount";
      type uint32;
      description "number of evpn->bp entries";
    }
    leaf evpn-to-unknown-count {
      xr:xr-xml-map "l2fib:EVPNToUnknownCount";
      type uint32;
      description "number of evpn->unknown type entries";
    }
    leaf ac-down-count-aib {
      xr:xr-xml-map "l2fib:ACDownCountAIB";
      type uint32;
      description "number of down acs with reason aib";
    }
    leaf ac-down-count-l2vpn {
      xr:xr-xml-map "l2fib:ACDownCountL2VPN";
      type uint32;
      description "number of down acs with reason l2vpn";
    }
    leaf ac-down-count-l3fib {
      xr:xr-xml-map "l2fib:ACDownCountL3FIB";
      type uint32;
      description "number of down acs with reason fib";
    }
    leaf ac-down-count-vpdn {
      xr:xr-xml-map "l2fib:ACDownCountVPDN";
      type uint32;
      description "number of down acs with reason vpdn";
    }
    leaf vpws-pw-invalid-xid-drop-count {
      xr:xr-xml-map "l2fib:VpwsPWInvalidXidDropCount";
      type uint32;
      description
        "number of xc updates dropped due to VPWS PW
        invalid xid";
    }
    leaf vpls-pw-invalid-xid-drop-count {
      xr:xr-xml-map "l2fib:VplsPWInvalidXidDropCount";
      type uint32;
      description
        "number of xc updates dropped due to VPLS PW
        invalid xid";
    }
    leaf virtual-ac-invalid-xid-drop-count {
      xr:xr-xml-map "l2fib:VirtualACInvalidXidDropCount";
      type uint32;
      description
        "number of xc updates dropped due to Virtual AC
        invalid xid";
    }
    leaf pbb-invalid-xid-drop-count {
      xr:xr-xml-map "l2fib:PBBInvalidXidDropCount";
      type uint32;
      description
        "number of xc updates dropped due to PBB invalid
        xid";
    }
    leaf vni-invalid-xid-drop-count {
      xr:xr-xml-map "l2fib:VNIInvalidXidDropCount";
      type uint32;
      description
        "number of xc updates dropped due to VNI invalid
        xid";
    }
    leaf evpn-invalid-xid-drop-count {
      xr:xr-xml-map "l2fib:EVPNInvalidXidDropCount";
      type uint32;
      description
        "number of xc updates dropped due to EVPN invalid
        xid";
    }
    leaf vpls-pw-max-exceeded-drop-cnt {
      xr:xr-xml-map "l2fib:VplsPWMaxExceededDropCnt";
      type uint32;
      description
        "number of xc updates dropped due to max VPLS PWs
        exceeded";
    }
    leaf bundle-ac-max-exceeded-drop-cnt {
      xr:xr-xml-map "l2fib:BundleACMaxExceededDropCnt";
      type uint32;
      description
        "number of xc updates dropped due to max Bundle
        ACs exceeded";
    }
    leaf p2p-count {
      xr:xr-xml-map "l2fib:P2PCount";
      type uint32;
      description "number of p2p xconnects";
    }
    leaf bp-count {
      xr:xr-xml-map "l2fib:BPCount";
      type uint32;
      description "number of bridge-port xconnects";
    }
    leaf pwhe-l2-if-count {
      xr:xr-xml-map "l2fib:PwheL2IfCount";
      type uint32;
      description "number of PWHE L2IF xconnects";
    }
  }

  grouping L2FIB-SUMMARY-INFO {
    description "L2FIB summary info";

    container xconnect-summary {
      description "xconnect db summary info";
      uses L2FIB-XC-SUMMARY-INFO;
    }

    container next-hop-summary {
      description "nhop db summry info";
      uses L2FIB-NH-SUMMARY-INFO;
    }

    container l2tp-disposition-summary {
      description "L2TP disposition object summary";
      uses L2FIB-L2TP-DISP-SUMMARY-INFO;
    }

    container bridge-domain-summary {
      description "Bridge-domain summary info";
      uses L2FIB-BD-SUMMARY-INFO;
    }

    container mac-summary {
      description "mac summary info";
      uses L2FIB-MAC-SUMMARY-INFO;
    }

    container queue-summary {
      description "queue summary info";
      uses L2FIB-OBJ-QUEUES-SUMMARY;
    }

    container evpn-summary {
      description "evpn summary info";
      uses L2FIB-EVPN-SUMMARY-INFO;
    }

    container global-cfg {
      description "Global configuration";
      uses L2FIB-GLOBAL-CFG-INFO;
    }

    container ptree-summary {
      description "P2MP PTree summary info";
      uses L2FIB-PTREE-SUMMARY-INFO;
    }

    container pw-group-summary {
      description "PWGroup summary info";
      uses L2FIB-PWGROUP-SUMMARY-INFO;
    }

    container pwhe-mp-summary {
      description "PWHE Main-port summary info";
      uses L2FIB-PWHE-MP-SUMMARY-INFO;
    }
  }

  grouping L2FIB-MCAST-XID-INFO {
    description "L2fib xid info";

    container base-information {
      description "Base Information";
      uses L2FIB-BASE-INFO;
    }

    container forward-stats {
      description "Forwarding Statistics";
      uses L2FIB-PLATFORM-STATS-BAG;
    }

    container source-prefix {
      description "Source Prefix";
      uses L2FIB-PREFIX-INFO;
    }

    container destination-prefix {
      description "Destination Prefix";
      uses L2FIB-PREFIX-INFO;
    }
    leaf bridge-id {
      xr:xr-xml-map "l2fib:BridgeID";
      type uint32;
      description "Bridge Id";
    }
    leaf ac-interface-handle {
      xr:xr-xml-map "l2fib:ACInterfaceHandle";
      type xr:Interface-name;
      description "AC If handle";
    }
    leaf leaf-pointer {
      xr:xr-xml-map "l2fib:LeafPointer";
      type uint32;
      description "Leaf Ptr";
    }
    leaf pw-id {
      xr:xr-xml-map "l2fib:PW_ID";
      type string {
        length "0..40";
      }
      description "PW ID";
    }
    leaf next-hop-address {
      xr:xr-xml-map "l2fib:NextHopAddress";
      type inet:ipv4-address;
      description "NHOP IP Address";
    }
    leaf isid {
      xr:xr-xml-map "l2fib:Isid";
      type uint32;
      description "Isid Id";
    }
    leaf csfl {
      xr:xr-xml-map "l2fib:Csfl";
      type uint32;
      description "Csfl Id";
    }
    leaf sat-id {
      xr:xr-xml-map "l2fib:satID";
      type uint16;
      description "Sat Id";
    }
    leaf is-ole-offloaded {
      xr:xr-xml-map "l2fib:isOleOffloaded";
      type boolean;
      description "Ole Offloaded";
    }
    leaf is-ole-master {
      xr:xr-xml-map "l2fib:isOleMaster";
      type boolean;
      description "Ole Master";
    }
    leaf is-topo-hub-and-spoke {
      xr:xr-xml-map "l2fib:isTopoHubAndSpoke";
      type boolean;
      description "Topo HubAndSpoke";
    }
  }

  grouping L2FIB-BRIDGE-SUMMARY-INFO {
    description "L2VPN bridge summary info";
    leaf bridge-id {
      xr:xr-xml-map "l2fib:BridgeID";
      type uint32;
      description "Bridge ID";
    }
    leaf bridge-name {
      xr:xr-xml-map "l2fib:BridgeName";
      type string;
      description "Bridge name";
    }
    leaf mac-limit {
      xr:xr-xml-map "l2fib:MACLimit";
      type uint32;
      description "MAC limit";
    }
    leaf mac-limit-action {
      xr:xr-xml-map "l2fib:MACLimitAction";
      type Mgmt-l2fib-mac-limit-action;
      description "MAC limit action";
    }
    leaf flood-disabled {
      xr:xr-xml-map "l2fib:FloodDisabled";
      type boolean;
      description "Is flooding disabled";
    }
    leaf mac-learning-disabled {
      xr:xr-xml-map "l2fib:MACLearningDisabled";
      type boolean;
      description "Is MAC learning disabled";
    }
    leaf mac-port-down-flush-disabled {
      xr:xr-xml-map "l2fib:MACPortDownFlushDisabled";
      type boolean;
      description "Is MAC port down flush disabled";
    }
    leaf admin-disabled {
      xr:xr-xml-map "l2fib:AdminDisabled";
      type boolean;
      description "Is administratively disabled";
    }
    leaf bridge-port-count {
      xr:xr-xml-map "l2fib:BridgePortCount";
      type uint32;
      description "Number of bridge ports";
    }
    leaf number-of-shg {
      xr:xr-xml-map "l2fib:NumberOfSHG";
      type uint32;
      description "Number of split horizon groups";
    }
    leaf number-of-hwmac {
      xr:xr-xml-map "l2fib:NumberOfHWMAC";
      type uint32;
      description "Number of HW MAC addresses";
    }
    leaf number-of-swmac {
      xr:xr-xml-map "l2fib:NumberOfSWMAC";
      type uint32;
      description "Number of SW MAC addresses";
    }
    leaf mtu {
      xr:xr-xml-map "l2fib:MTU";
      type uint32;
      description "MTU";
    }
    leaf aging-time-out {
      xr:xr-xml-map "l2fib:AgingTimeOut";
      type uint32;
      description "Aging timeout";
    }
    leaf msti {
      xr:xr-xml-map "l2fib:MSTI";
      type uint32;
      description "multi-spanning tree instance";
    }
  }

  grouping L2FIB-BRIDGE-PORT-SEG-UN {
    description "L2FIB BRIDGE PORT SEG UN";

    container ac {
      when "../data-type = 'mgmt-l2fib-data-type-ac'" {
        description "../DataType = 'MGMT_L2FIB_DATA_TYPE_AC'";
      }
      description "ac";
      uses L2FIB-AC-INFO;
    }

    container pbb {
      when "../data-type = 'mgmt-l2fib-data-type-pbb'" {
        description "../DataType = 'MGMT_L2FIB_DATA_TYPE_PBB'";
      }
      description "pbb";
      uses L2FIB-PBB-INFO;
    }

    container vni {
      when "../data-type = 'mgmt-l2fib-data-type-vni'" {
        description "../DataType = 'MGMT_L2FIB_DATA_TYPE_VNI'";
      }
      description "vni";
      uses L2FIB-VNI-INFO;
    }

    container evpn {
      when "../data-type = 'mgmt-l2fib-data-type-evpn'" {
        description "../DataType = 'MGMT_L2FIB_DATA_TYPE_EVPN'";
      }
      description "evpn";
      uses L2FIB-EVPN-INFO;
    }

    container pw {
      when "../data-type != 'mgmt-l2fib-data-type-ac' and"+
        " ../data-type != 'mgmt-l2fib-data-type-pbb' and"+
        " ../data-type != 'mgmt-l2fib-data-type-vni' and"+
        " ../data-type != 'mgmt-l2fib-data-type-evpn'" {
          description
            "../DataType != 'MGMT_L2FIB_DATA_TYPE_AC' and .
            ./DataType != 'MGMT_L2FIB_DATA_TYPE_PBB' and .
            ./DataType != 'MGMT_L2FIB_DATA_TYPE_VNI' and .
            ./DataType != 'MGMT_L2FIB_DATA_TYPE_EVPN'";
      }
      description "pw";
      uses L2FIB-PW-INFO;
    }
    leaf data-type {
      xr:xr-xml-map "l2fib:DataType";
      type Mgmt-l2fib-data;
      description "DataType";
    }
  }

  grouping L2FIB-BRIDGE-PORT-DETAIL-INFO {
    description "L2VPN bridge port info";

    container segment {
      description "Segment";
      uses L2FIB-BRIDGE-PORT-SEG-UN;
    }

    container bridge-port-operational-info {
      description "Bridge port operational information";
      uses L2FIB-OPER-BRIDGE-PORT-INFO;
    }
    leaf bridge-id {
      xr:xr-xml-map "l2fib:BridgeID";
      type uint32;
      description "Bridge ID";
    }
    leaf shg-id {
      xr:xr-xml-map "l2fib:SHG_ID";
      type uint32;
      description "Split horizon group ID";
    }
    leaf xc-id {
      xr:xr-xml-map "l2fib:XC_ID";
      type uint32;
      description "xconnect ID";
    }
    leaf number-of-hw-mac {
      xr:xr-xml-map "l2fib:NumberOfHW_MAC";
      type uint32;
      description "Number of HW MAC addresses";
    }
    leaf number-of-sw-mac {
      xr:xr-xml-map "l2fib:NumberOfSW_MAC";
      type uint32;
      description "Number of SW MAC addresses";
    }
    leaf mac-limit {
      xr:xr-xml-map "l2fib:MACLimit";
      type uint32;
      description "MAC limit";
    }
    leaf mac-limit-action {
      xr:xr-xml-map "l2fib:MACLimitAction";
      type Mgmt-l2fib-mac-limit-action;
      description "MAC limit action";
    }
    leaf flooding-disabled {
      xr:xr-xml-map "l2fib:FloodingDisabled";
      type boolean;
      description "Is flooding disabled";
    }
    leaf mac-learning-disabled {
      xr:xr-xml-map "l2fib:MACLearningDisabled";
      type boolean;
      description "Is MAC learning disabled";
    }
    leaf mac-port-down-flush-disabled {
      xr:xr-xml-map "l2fib:MACPortDownFlushDisabled";
      type boolean;
      description "Is MAC port down flush disabled";
    }
    leaf mtu {
      xr:xr-xml-map "l2fib:MTU";
      type uint32;
      description "MTU";
    }
    leaf aging-time-out {
      xr:xr-xml-map "l2fib:AgingTimeOut";
      type uint32;
      description "Aging timeout";
    }
  }

  grouping L2FIB-G8032-RING-INSTANCE-DETAIL-INFO {
    description "L2FIB ethernet ring instance info detail";
    leaf ring-instance {
      xr:xr-xml-map "l2fib:RingInstance";
      type uint32;
      description "Ring instance number";
    }
    leaf vlan-ids {
      xr:xr-xml-map "l2fib:VlanIDs";
      type string;
      description "Vlan Ids";
    }
    leaf ring-profile {
      xr:xr-xml-map "l2fib:RingProfile";
      type string;
      description "Ring Profile";
    }
    leaf rpl {
      xr:xr-xml-map "l2fib:RPL";
      type L2fib-g8032-rpl;
      description "RPL";
    }
    leaf aps-port0 {
      xr:xr-xml-map "l2fib:ApsPort0";
      type string;
      description "Port 0 of aps-channel";
    }
    leaf aps-port1 {
      xr:xr-xml-map "l2fib:ApsPort1";
      type string;
      description "Port 1 of aps-channel";
    }
    leaf aps-port-status0 {
      xr:xr-xml-map "l2fib:ApsPortStatus0";
      type L2fib-g8032-aps-port-status;
      description "Status of Port 0";
    }
    leaf aps-port-status1 {
      xr:xr-xml-map "l2fib:ApsPortStatus1";
      type L2fib-g8032-aps-port-status;
      description "Status of Port 1";
    }
    leaf aps-channel-level {
      xr:xr-xml-map "l2fib:APSChannelLevel";
      type uint32;
      description "APS channel level";
    }
  }

  grouping L2FIB-G8032-RING-INSTANCE-SUMMARY-INFO {
    description "L2FIB ethernet ring instance info summary";
    leaf ring-instance {
      xr:xr-xml-map "l2fib:RingInstance";
      type uint32;
      description "Ring instance number";
    }
    leaf aps-port0 {
      xr:xr-xml-map "l2fib:ApsPort0";
      type string;
      description "Port 0 of aps-channel";
    }
    leaf aps-port1 {
      xr:xr-xml-map "l2fib:ApsPort1";
      type string;
      description "Port 1 of aps-channel";
    }
  }

  grouping L2FIB-G8032-RING-SUMMARY-INFO {
    description "L2FIB ethernet ring info summary";
    leaf ring-name {
      xr:xr-xml-map "l2fib:RingName";
      type string;
      description "Name of the ring";
    }
    leaf port0 {
      xr:xr-xml-map "l2fib:Port0";
      type string;
      description "Port 0";
    }
    leaf port1 {
      xr:xr-xml-map "l2fib:Port1";
      type string;
      description "Port 1";
    }
  }

  grouping L2FIB-G8032-RING-DETAIL-INFO {
    description "L2FIB ethernet ring info detail";
    leaf ring-name {
      xr:xr-xml-map "l2fib:RingName";
      type string;
      description "Name of the ring";
    }
    leaf port0 {
      xr:xr-xml-map "l2fib:Port0";
      type string;
      description "Port 0";
    }
    leaf port1 {
      xr:xr-xml-map "l2fib:Port1";
      type string;
      description "Port 1";
    }
    leaf monitor0 {
      xr:xr-xml-map "l2fib:Monitor0";
      type string;
      description "Monitor port 0";
    }
    leaf monitor1 {
      xr:xr-xml-map "l2fib:Monitor1";
      type string;
      description "Monitor port 1";
    }
    leaf is-open-ring {
      xr:xr-xml-map "l2fib:IsOpenRing";
      type boolean;
      description "Open Ring";
    }
  }

  grouping L2FIB-L2TP-DISP-INFO {
    description "L2TP session disposition object";

    container base {
      description "Base information";
      uses L2FIB-BASE-INFO;
    }
    leaf session-id-xr {
      xr:xr-xml-map "l2fib:session-id-xr";
      type uint32;
      description "Local Session Id";
    }
    leaf interface-handle {
      xr:xr-xml-map "l2fib:InterfaceHandle";
      type xr:Interface-name;
      description "Interface handle of egress main interface";
    }
    leaf sub-interface-name {
      xr:xr-xml-map "l2fib:SubInterfaceName";
      type xr:Interface-name;
      description "SubInterface Name";
    }
    leaf source-address {
      xr:xr-xml-map "l2fib:SourceAddress";
      type inet:ipv4-address;
      description "Source/Local IP address of the tunnel";
    }
    leaf bound {
      xr:xr-xml-map "l2fib:Bound";
      type boolean;
      description "Bind status";
    }
    leaf tunnel-id-xr {
      xr:xr-xml-map "l2fib:tunnel-id-xr";
      type uint32;
      description "Tunnel ID, l2tpv2";
    }
    leaf ipv4-table-id {
      xr:xr-xml-map "l2fib:IPv4TableId";
      type uint32;
      description "IPv4 Table ID";
    }
    leaf ipv6-table-id {
      xr:xr-xml-map "l2fib:IPv6TableId";
      type uint32;
      description "IPv6 Table ID";
    }
    leaf nhop-ip-addr {
      xr:xr-xml-map "l2fib:NhopIpAddr";
      type inet:ipv4-address;
      description "NHOP IP Address of the tunnel";
    }
    leaf session-type {
      xr:xr-xml-map "l2fib:SessionType";
      type L2fib-l2tp-session;
      description "L2tp or L2tpv2 session";
    }
  }

  grouping L2FIB-MAIN-PORT-MSTP-DETAIL-INFO {
    description "L2FIB main port mstp detail info";

    container base {
      description "Base information";
      uses L2FIB-BASE-INFO;
    }
    leaf parent-interface-xr {
      xr:xr-xml-map "l2fib:parent-interface-xr";
      type xr:Interface-name;
      description "main port ID";
    }
    leaf msti-xr {
      xr:xr-xml-map "l2fib:msti-xr";
      type uint32;
      description "multi-spanning tree instance configured value";
    }
    leaf internal-msti {
      xr:xr-xml-map "l2fib:InternalMSTI";
      type uint32;
      description "multi-spanning tree instance internal value";
    }
    leaf state {
      xr:xr-xml-map "l2fib:State";
      type uint32;
      description "MSTI state";
    }
    leaf learn-key {
      xr:xr-xml-map "l2fib:LearnKey";
      type uint8;
      description "Learn Key";
    }
    leaf-list bridge-port-array {
      xr:xr-xml-map "l2fib:BridgePortArray";
      type xr:Interface-name;
      description "Bridge port";
    }
  }

  grouping L2FIB-MAIN-INTERFACE-INSTANCE-BPORT-SUMMARY-INFO {
    description
      "L2VPN main interface instance bridge port info
      summary";
    leaf bridge-port-id {
      xr:xr-xml-map "l2fib:BridgePortID";
      type xr:Interface-name;
      description "Bridge Port ID";
    }
    leaf bridge-id {
      xr:xr-xml-map "l2fib:BridgeID";
      type uint32;
      description "Bridge ID";
    }
    leaf main-interface {
      xr:xr-xml-map "l2fib:MainInterface";
      type xr:Interface-name;
      description "Main interface ID";
    }
    leaf bp-type {
      xr:xr-xml-map "l2fib:BPType";
      type uint8;
      description "Bridge Port Type";
    }
  }

  grouping L2FIB-MAIN-INTERFACE-INSTANCE-SUMMARY-INFO {
    description
      "L2FIB main interface instance summary info
      summary";
    leaf main-interface {
      xr:xr-xml-map "l2fib:MainInterface";
      type xr:Interface-name;
      description "Main interface ID";
    }
    leaf instance {
      xr:xr-xml-map "l2fib:Instance";
      type uint32;
      description "Interface instance";
    }
    leaf state {
      xr:xr-xml-map "l2fib:State";
      type L2fib-main-if-instance-state;
      description "Instance state";
    }
    leaf bridge-port-count {
      xr:xr-xml-map "l2fib:BridgePortCount";
      type uint32;
      description "Number of bridge ports";
    }
    leaf instance-provisioned {
      xr:xr-xml-map "l2fib:InstanceProvisioned";
      type boolean;
      description "Instances provisioned flag";
    }
  }

  grouping L2FIB-MAIN-INTERFACE-INSTANCE-BPORT-DETAIL-INFO {
    description
      "L2VPN main interface instance bridge port info
      detail";

    container oper {
      description "Operational information";
      uses L2FIB-OPER-BRIDGE-PORT-INFO;
    }
    leaf bridge-port-id {
      xr:xr-xml-map "l2fib:BridgePortID";
      type xr:Interface-name;
      description "Bridge Port ID";
    }
    leaf bridge-id {
      xr:xr-xml-map "l2fib:BridgeID";
      type uint32;
      description "Bridge ID";
    }
    leaf state {
      xr:xr-xml-map "l2fib:State";
      type L2fib-main-if-instance-state;
      description "Instance state";
    }
    leaf main-interface {
      xr:xr-xml-map "l2fib:MainInterface";
      type xr:Interface-name;
      description "Main interface ID";
    }
    leaf bp-type {
      xr:xr-xml-map "l2fib:BPType";
      type uint8;
      description "Bridge Port Type";
    }
  }

  grouping L2FIB-MAIN-INTERFACE-INSTANCE-DETAIL-INFO {
    description "L2FIB main interface instance detail info detail";
    leaf main-interface {
      xr:xr-xml-map "l2fib:MainInterface";
      type xr:Interface-name;
      description "Main interface ID";
    }
    leaf instance {
      xr:xr-xml-map "l2fib:Instance";
      type uint32;
      description "Interface instance";
    }
    leaf state {
      xr:xr-xml-map "l2fib:State";
      type L2fib-main-if-instance-state;
      description "Instance state";
    }
    leaf bridge-port-count {
      xr:xr-xml-map "l2fib:BridgePortCount";
      type uint32;
      description "Number of bridge ports";
    }
    leaf instance-provisioned {
      xr:xr-xml-map "l2fib:InstanceProvisioned";
      type boolean;
      description "Instances provisioned flag";
    }
  }

  grouping L2FIB-MAIN-INTERFACE-SUMMARY-INFO {
    description "L2FIB main interface summary info summary";
    leaf main-interface {
      xr:xr-xml-map "l2fib:MainInterface";
      type xr:Interface-name;
      description "Main Interface ID";
    }
    leaf-list instance-id {
      xr:xr-xml-map "l2fib:InstanceId";
      type uint32;
      description "Instance IDs";
    }
    leaf-list instances-state {
      xr:xr-xml-map "l2fib:InstancesState";
      type L2fib-main-if-instance-state;
      description "State for each instance";
    }
    leaf-list instances-provisioned {
      xr:xr-xml-map "l2fib:InstancesProvisioned";
      type boolean;
      description "Instances provisioned flag";
    }
  }

  grouping L2FIB-MAIN-INTERFACE-DETAIL-INFO {
    description "L2FIB main interface detail info detail";
    leaf main-interface {
      xr:xr-xml-map "l2fib:MainInterface";
      type xr:Interface-name;
      description "Main Interface ID";
    }
    leaf mac {
      xr:xr-xml-map "l2fib:MAC";
      type string;
      description "MAC Address";
    }
    leaf esi-id {
      xr:xr-xml-map "l2fib:EsiID";
      type uint16;
      description "Ethernet segment ID";
    }
    leaf-list instance-id {
      xr:xr-xml-map "l2fib:InstanceId";
      type uint32;
      description "Instance IDs";
    }
    leaf-list instances-state {
      xr:xr-xml-map "l2fib:InstancesState";
      type L2fib-main-if-instance-state;
      description "State for each instance";
    }
    leaf-list instances-provisioned {
      xr:xr-xml-map "l2fib:InstancesProvisioned";
      type boolean;
      description "Instances provisioned flag";
    }
    leaf-list bridge-port-count-instance {
      xr:xr-xml-map "l2fib:BridgePortCountInstance";
      type uint32;
      description "Number of bridge ports per instance";
    }
  }

  grouping L2FIB-DHCP-BIND-UN {
    description "L2FIB DHCP BIND UN";

    container ac {
      when "../data-type = 'mgmt-l2fib-data-type-ac'" {
        description "../DataType = 'MGMT_L2FIB_DATA_TYPE_AC'";
      }
      description "ac";
      uses L2FIB-AC-KEY-INFO;
    }

    container pw {
      when "../data-type != 'mgmt-l2fib-data-type-ac'" {
        description "../DataType != 'MGMT_L2FIB_DATA_TYPE_AC'";
      }
      description "pw";
      uses L2FIB-PW-KEY-INFO;
    }
    leaf data-type {
      xr:xr-xml-map "l2fib:DataType";
      type Mgmt-l2fib-data;
      description "DataType";
    }
  }

  grouping L2FIB-DHCP-BINDING-DETAIL-INFO {
    description "L2FIB DHCP binding detail info";

    container base {
      description "Base information";
      uses L2FIB-BASE-INFO;
    }

    container port {
      description "Union of Port information";
      uses L2FIB-DHCP-BIND-UN;
    }
  }

  grouping L2FIB-PWGROUP-INFO {
    description "l2fib pwgroup info";
    leaf group-state {
      xr:xr-xml-map "l2fib:GroupState";
      type L2fib-group-state;
      description "Group State";
    }
    leaf pw-list-count {
      xr:xr-xml-map "l2fib:PwListCount";
      type uint32;
      description "Dependent PW List Count";
    }
  }

  grouping L2FIB-RSRC-SHM-INFO {
    description "Shared memory availability";
    leaf oout-of-resource-mode {
      xr:xr-xml-map "l2fib:OoutOfResourceMode";
      type uint32;
      description "OOR mode";
    }
    leaf maximum-available {
      xr:xr-xml-map "l2fib:MaximumAvailable";
      type uint64;
      units "byte";
      description "Maximum bytes available";
    }
    leaf average-available {
      xr:xr-xml-map "l2fib:AverageAvailable";
      type uint64;
      units "byte";
      description "Average number of bytes available";
    }
    leaf average-utility {
      xr:xr-xml-map "l2fib:AverageUtility";
      type uint64;
      description "Average utilization";
    }
  }

  grouping L2FIB-RSRC-INFO {
    description "L2FIB resource availability info";

    container shm-resource {
      description "Shared memory resource info";
      uses L2FIB-RSRC-SHM-INFO;
    }
    leaf overall-out-of-resource-mode {
      xr:xr-xml-map "l2fib:OverallOutOfResourceMode";
      type uint32;
      description "Overall OOR mode";
    }
    leaf hardware-resource-mode-information {
      xr:xr-xml-map "l2fib:HardwareResourceModeInformation";
      type yang:hex-string;
      description "Opaque hardware resource info";
    }
    leaf-list hardware-resource-mode {
      xr:xr-xml-map "l2fib:HardwareResourceMode";
      type uint32;
      description "Hardware resource mode";
    }
  }

  grouping L2FIB-MAIN-PORT-MSTP-SUMMARY-INFO {
    description "L2FIB main port mstp summary info";

    container base {
      description "Base information";
      uses L2FIB-BASE-INFO;
    }
    leaf parent-interface-xr {
      xr:xr-xml-map "l2fib:parent-interface-xr";
      type xr:Interface-name;
      description "main port ID";
    }
    leaf msti-xr {
      xr:xr-xml-map "l2fib:msti-xr";
      type uint32;
      description "multi-spanning tree instance";
    }
    leaf state {
      xr:xr-xml-map "l2fib:State";
      type uint32;
      description "MSTI state";
    }
    leaf bridge-port-count {
      xr:xr-xml-map "l2fib:BridgePortCount";
      type uint32;
      description "Number of bridge ports";
    }
  }

  grouping L2FIB-BRIDGE-P2MP-PW-INFO {
    description "L2FIB BRIDGE P2MP PW INFO";

    container parent-next-hop {
      description "Parent Next Hop for P2MP PW";
      uses L2FIB-NHOP-INFO;
    }
    leaf ptree-type {
      xr:xr-xml-map "l2fib:PTreeType";
      type L2vpn-ptree;
      description "P2MP ptree type";
    }
    leaf lsm-id {
      xr:xr-xml-map "l2fib:LSM_ID";
      type uint32;
      description "LSM id";
    }
    leaf p2mp-te-interface {
      xr:xr-xml-map "l2fib:P2MP_TEInterface";
      type xr:Interface-name;
      description "P2MP TE ifh";
    }
    leaf parent-nh-valid {
      xr:xr-xml-map "l2fib:ParentNHValid";
      type boolean;
      description "Is Parent NH Valid";
    }
    leaf parent-nh-bound {
      xr:xr-xml-map "l2fib:ParentNHBound";
      type boolean;
      description "Is Parent NH Bound";
    }
    leaf local-label {
      xr:xr-xml-map "l2fib:LocalLabel";
      type uint32;
      description "Local label";
    }
  }

  grouping L2FIB-BRIDGE-BVI-INFO {
    description "L2FIB BRIDGE BVI INFO";
    leaf bvi-ifh {
      xr:xr-xml-map "l2fib:BVIIfh";
      type xr:Interface-name;
      description "BVI interface handle";
    }
    leaf bvi-xid {
      xr:xr-xml-map "l2fib:BVIXid";
      type uint32;
      description "BVI xconnect id";
    }
    leaf bvi-name {
      xr:xr-xml-map "l2fib:BVIName";
      type string {
        length "0..65";
      }
      description "BVI name";
    }
    leaf irb-plat-data-len {
      xr:xr-xml-map "l2fib:IRBPlatDataLen";
      type uint32;
      units "byte";
      description "Platform data bytes";
    }
    leaf irb-plat-data {
      xr:xr-xml-map "l2fib:IRBPlatData";
      type yang:hex-string;
      description "IRB platform data";
    }
  }

  grouping L2FIB-BRIDGE-PBB-CORE {
    description "L2FIB BRIDGE PBB CORE";
    leaf nber-edge-bd {
      xr:xr-xml-map "l2fib:nberEdgeBd";
      type uint32;
      description "Number of associated pbb-edge Bds";
    }
  }

  grouping L2FIB-BRIDGE-PBB-EDGE {
    description "L2FIB BRIDGE PBB EDGE";
    leaf i-sid {
      xr:xr-xml-map "l2fib:I_SID";
      type uint32;
      description "I SID";
    }
    leaf core-bd-name {
      xr:xr-xml-map "l2fib:CoreBdName";
      type string;
      description "Core Bridge Domain name";
    }
    leaf mirp-lite-rx {
      xr:xr-xml-map "l2fib:MIRPLiteRx";
      type uint64;
      description "MIRP-lite Rx packet counter";
    }
    leaf mirp-lite-tx {
      xr:xr-xml-map "l2fib:MIRPLiteTx";
      type uint64;
      description "MIRP-lite Tx packet counter";
    }
  }

  grouping L2FIB-BRIDGE-PBB-UN {
    description "L2FIB BRIDGE PBB UN";

    container edge {
      when "../pbb-type = 'mgmt-l2fib-bridge-type-pbb-edge'" {
        description
          "../PbbType = 'MGMT_L2FIB_BRIDGE_TYPE_PBB_EDGE'";
      }
      description "edge";
      uses L2FIB-BRIDGE-PBB-EDGE;
    }

    container core {
      when "../pbb-type = 'mgmt-l2fib-bridge-type-pbb-core'" {
        description
          "../PbbType = 'MGMT_L2FIB_BRIDGE_TYPE_PBB_CORE'";
      }
      description "core";
      uses L2FIB-BRIDGE-PBB-CORE;
    }
    leaf pbb-type {
      xr:xr-xml-map "l2fib:PbbType";
      type Mgmt-l2fib-bridge;
      description "PbbType";
    }
  }

  grouping L2FIB-OPER-BRIDGE-INFO {
    description "L2VPN bridge operational information";

    container operational-information {
      description "L2 operational information";
      uses L2FIB-OPER-INFO;
    }
    leaf unicast-storm-control-pps {
      xr:xr-xml-map "l2fib:UnicastStormControlPPS";
      type uint64;
      description "Unicast storm control pps";
    }
    leaf unicast-storm-control-kb-ps {
      xr:xr-xml-map "l2fib:UnicastStormControlKbPS";
      type uint64;
      units "kbit/s";
      description "Unicast storm control kbps";
    }
    leaf broadcast-storm-control-pps {
      xr:xr-xml-map "l2fib:BroadcastStormControlPPS";
      type uint64;
      description "Broadcast storm control pps";
    }
    leaf broadcast-storm-control-kb-ps {
      xr:xr-xml-map "l2fib:BroadcastStormControlKbPS";
      type uint64;
      units "kbit/s";
      description "Broadcast storm control kbps";
    }
    leaf multicast-storm-control-pps {
      xr:xr-xml-map "l2fib:MulticastStormControlPPS";
      type uint64;
      description "Multicast storm control pps";
    }
    leaf multicast-storm-control-kb-ps {
      xr:xr-xml-map "l2fib:MulticastStormControlKbPS";
      type uint64;
      units "kbit/s";
      description "Multicast storm control kbps";
    }
  }

  grouping L2FIB-BRIDGE-INFO {
    description "L2VPN bridge detailed info";

    container base {
      description "Base information";
      uses L2FIB-BASE-INFO;
    }

    container oper {
      description "Operational information";
      uses L2FIB-OPER-BRIDGE-INFO;
    }

    container bd-pbb-union {
      description "Union of bridge Edge and Core info";
      uses L2FIB-BRIDGE-PBB-UN;
    }

    container bvi-info {
      description "BVI Information";
      uses L2FIB-BRIDGE-BVI-INFO;
    }

    container p2mppw-info {
      description "P2MP PW Information";
      uses L2FIB-BRIDGE-P2MP-PW-INFO;
    }
    leaf bridge-id {
      xr:xr-xml-map "l2fib:BridgeID";
      type uint32;
      description "Bridge ID";
    }
    leaf bridge-port-count {
      xr:xr-xml-map "l2fib:BridgePortCount";
      type uint32;
      description "Number of bridge ports";
    }
    leaf number-of-hwmac {
      xr:xr-xml-map "l2fib:NumberOfHWMAC";
      type uint32;
      description "Number of HW MAC addresses";
    }
    leaf number-of-swmac {
      xr:xr-xml-map "l2fib:NumberOfSWMAC";
      type uint32;
      description "Number of SW MAC addresses";
    }
    leaf bridge-name {
      xr:xr-xml-map "l2fib:BridgeName";
      type string;
      description "Bridge name";
    }
    leaf shg-count {
      xr:xr-xml-map "l2fib:SHGCount";
      type uint32;
      description "Number of split horizon groups";
    }
    leaf bridge-type {
      xr:xr-xml-map "l2fib:BridgeType";
      type Mgmt-l2fib-bridge;
      description "Bridge Type";
    }
    leaf learn-key {
      xr:xr-xml-map "l2fib:LearnKey";
      type uint8;
      description "Learn Key";
    }
  }

  grouping L2FIB-DHCP-BINDING-COUNT-INFO {
    description "L2FIB DHCP binding count info";
    leaf bindings {
      xr:xr-xml-map "l2fib:Bindings";
      type uint32;
      description "DHCP binding count";
    }
  }

  grouping L2FIB-PWHE-MP-SHOW-INFO {
    description "L2FIB PWHE Main-port info";
    leaf next-hop-valid {
      xr:xr-xml-map "l2fib:NextHopValid";
      type boolean;
      description "IS Next Hop Valid";
    }
    leaf next-hop-address {
      xr:xr-xml-map "l2fib:NextHopAddress";
      type inet:ipv4-address;
      description "Next Hop Address";
    }
    leaf pseudo-wire-type {
      xr:xr-xml-map "l2fib:PseudoWireType";
      type uint32;
      description "Pseudowire type";
    }
    leaf generic-interface-list-id {
      xr:xr-xml-map "l2fib:GenericInterfaceListID";
      type uint32;
      description "Generic Interface List ID";
    }
    leaf internal-label {
      xr:xr-xml-map "l2fib:InternalLabel";
      type uint32;
      description "Internal label";
    }
    leaf remote-label {
      xr:xr-xml-map "l2fib:RemoteLabel";
      type uint32;
      description "Remote label";
    }
    leaf control-word-enabled {
      xr:xr-xml-map "l2fib:ControlWordEnabled";
      type boolean;
      description "Control Word Enabled";
    }
  }

  grouping L2FIB-BRIDGE-MAC-EVPN-CTX-UN {
    description "L2FIB BRIDGE MAC EVPN CTX UN";

    container mcast-ole {
      when "../data-type = 'mgmt-l2fib-bridge-mac-evpn-ctx-moi'" {
        description
          "../DataType =
          'MGMT_L2FIB_BRIDGE_MAC_EVPN_CTX_MOI'";
      }
      description "mcast ole";
      uses L2VPN-EVPN-MOI-INFO;
    }
    leaf data-type {
      xr:xr-xml-map "l2fib:DataType";
      type Mgmt-l2fib-bridge-mac-evpn-ctx;
      description "DataType";
    }
    leaf esi-id {
      xr:xr-xml-map "l2fib:EsiID";
      when "../data-type ="+
        " 'mgmt-l2fib-bridge-mac-evpn-ctx-esi-id'" {
          description
            "../DataType =
            'MGMT_L2FIB_BRIDGE_MAC_EVPN_CTX_ESI_ID'";
      }
      type uint16;
      description "EsiID";
    }
    leaf local-label {
      xr:xr-xml-map "l2fib:LocalLabel";
      when "../data-type ="+
        " 'mgmt-l2fib-bridge-mac-evpn-ctx-local-label'" {
          description
            "../DataType =
            'MGMT_L2FIB_BRIDGE_MAC_EVPN_CTX_LOCAL_LABEL'";
      }
      type uint32;
      description "LocalLabel";
    }
  }

  grouping L2FIB-PW-KEY-INFO {
    description "L2FIB PW KEY INFO";
    leaf pw-id {
      xr:xr-xml-map "l2fib:PW_ID";
      type uint64;
      description "Pseudowire ID";
    }
    leaf next-hop-address {
      xr:xr-xml-map "l2fib:NextHopAddress";
      type inet:ipv4-address;
      description "Next Hop Address";
    }
    leaf pseudo-wire-id-type {
      xr:xr-xml-map "l2fib:PseudoWireIDType";
      type L2fib-pw-id;
      description "Pseudowire ID type";
    }
  }

  grouping L2FIB-EVPN-KEY-INFO {
    description "L2FIB EVPN KEY INFO";
    leaf xcid {
      xr:xr-xml-map "l2fib:XCID";
      type uint32;
      description "Xconnect ID";
    }
  }

  grouping L2FIB-VNI-KEY-INFO {
    description "L2FIB VNI KEY INFO";
    leaf xcid {
      xr:xr-xml-map "l2fib:XCID";
      type uint32;
      description "Xconnect ID";
    }
    leaf parent-if {
      xr:xr-xml-map "l2fib:ParentIF";
      type xr:Interface-name;
      description "Parent NVE Interface";
    }
  }

  grouping L2FIB-PBB-KEY-INFO {
    description "L2FIB PBB KEY INFO";
    leaf xcid {
      xr:xr-xml-map "l2fib:XCID";
      type uint32;
      description "Xconnect ID";
    }
  }

  grouping L2FIB-AC-KEY-INFO {
    description "L2FIB AC KEY INFO";
    leaf interface-handle {
      xr:xr-xml-map "l2fib:InterfaceHandle";
      type xr:Interface-name;
      description "Interface Handle";
    }
  }

  grouping L2FIB-BRIDGE-PORT-SEG-KEY-UN {
    description "L2FIB BRIDGE PORT SEG KEY UN";

    container ac {
      when "../data-type = 'mgmt-l2fib-data-type-ac'" {
        description "../DataType = 'MGMT_L2FIB_DATA_TYPE_AC'";
      }
      description "ac";
      uses L2FIB-AC-KEY-INFO;
    }

    container pbb {
      when "../data-type = 'mgmt-l2fib-data-type-pbb'" {
        description "../DataType = 'MGMT_L2FIB_DATA_TYPE_PBB'";
      }
      description "pbb";
      uses L2FIB-PBB-KEY-INFO;
    }

    container vni {
      when "../data-type = 'mgmt-l2fib-data-type-vni'" {
        description "../DataType = 'MGMT_L2FIB_DATA_TYPE_VNI'";
      }
      description "vni";
      uses L2FIB-VNI-KEY-INFO;
    }

    container evpn {
      when "../data-type = 'mgmt-l2fib-data-type-evpn'" {
        description "../DataType = 'MGMT_L2FIB_DATA_TYPE_EVPN'";
      }
      description "evpn";
      uses L2FIB-EVPN-KEY-INFO;
    }

    container pw {
      when "../data-type != 'mgmt-l2fib-data-type-ac' and"+
        " ../data-type != 'mgmt-l2fib-data-type-pbb' and"+
        " ../data-type != 'mgmt-l2fib-data-type-vni' and"+
        " ../data-type != 'mgmt-l2fib-data-type-evpn'" {
          description
            "../DataType != 'MGMT_L2FIB_DATA_TYPE_AC' and .
            ./DataType != 'MGMT_L2FIB_DATA_TYPE_PBB' and .
            ./DataType != 'MGMT_L2FIB_DATA_TYPE_VNI' and .
            ./DataType != 'MGMT_L2FIB_DATA_TYPE_EVPN'";
      }
      description "pw";
      uses L2FIB-PW-KEY-INFO;
    }
    leaf data-type {
      xr:xr-xml-map "l2fib:DataType";
      type Mgmt-l2fib-data;
      description "DataType";
    }
  }

  grouping L2FIB-BRIDGE-MAC-INFO {
    description "L2VPN bridge MAC address info";

    container base {
      description "Base information";
      uses L2FIB-BASE-INFO;
    }

    container segment {
      description "Segment";
      uses L2FIB-BRIDGE-PORT-SEG-KEY-UN;
    }

    container evpn-ctx {
      description "Evpn Context";
      uses L2FIB-BRIDGE-MAC-EVPN-CTX-UN;
    }

    container next-hop {
      description "Next Hop";
      uses L2FIB-NHOP-INFO;
    }
    leaf platform-is-hw-learn {
      xr:xr-xml-map "l2fib:PlatformIsHwLearn";
      type uint8;
      description "Platform is HW Learn";
    }
    leaf node-id {
      xr:xr-xml-map "l2fib:NodeID";
      type xr:Node-id;
      description "Nodeid list";
    }
    leaf bridge-domain-name {
      xr:xr-xml-map "l2fib:BridgeDomainName";
      type string;
      description "Bridge name";
    }
    leaf bridge-id {
      xr:xr-xml-map "l2fib:BridgeID";
      type uint32;
      description "Bridge ID";
    }
    leaf bmac-configured {
      xr:xr-xml-map "l2fib:BmacConfigured";
      type boolean;
      description "Flag: Configured BMAC";
    }
    leaf vni-l3-flag {
      xr:xr-xml-map "l2fib:VniL3Flag";
      type boolean;
      description "Flag: L3 Vxlan";
    }
    leaf pbb-bmac {
      xr:xr-xml-map "l2fib:pbbBMAC";
      type yang:mac-address;
      description "Backbone MAC Address";
    }
    leaf l3-encapsulationvlan-id {
      xr:xr-xml-map "l2fib:L3EncapsulationVlanID";
      type uint16;
      description "L3 encapsulation Vlan ID";
    }
    leaf next-hop-valid {
      xr:xr-xml-map "l2fib:NextHopValid";
      type boolean;
      description "IS Next Hop Valid";
    }
    leaf peer-vtep-ip {
      xr:xr-xml-map "l2fib:PeerVTEP_IP";
      type inet:ipv4-address;
      description "Peer VTEP IP for this MAC Address";
    }
    leaf flag-extension {
      xr:xr-xml-map "l2fib:FlagExtension";
      type uint8;
      description "MAC Flag Extension";
    }
    leaf vni {
      xr:xr-xml-map "l2fib:VNI";
      type uint32;
      description "VNI Information";
    }
  }

  grouping L2VPN-EVPN-MOI-INFO {
    description "L2VPN EVPN MOI INFO";
    leaf next-hop-ipv6-addr {
      xr:xr-xml-map "l2fib:NextHopIPv6Addr";
      type inet:ipv6-address;
      description "Next Hop IPv6 address";
    }
    leaf mcast-label {
      xr:xr-xml-map "l2fib:MCastLabel";
      type uint32;
      description "Inclusive mcast label";
    }
  }

  grouping L2FIB-EVPN-MCAST-OLE-INFO {
    description "L2FIB evpn mcast ole info";

    container mcast-ole {
      description "Mcast Ole Info";
      uses L2VPN-EVPN-MOI-INFO;
    }

    container next-hop {
      description "Next Hop";
      uses L2FIB-NHOP-INFO;
    }
    leaf is-bound {
      xr:xr-xml-map "l2fib:IsBound";
      type boolean;
      description "Is bound";
    }
    leaf next-hop-valid {
      xr:xr-xml-map "l2fib:NextHopValid";
      type boolean;
      description "IS Next Hop Valid";
    }
  }

  grouping L2FIB-EVPN-MCAST-LEAF-INFO {
    description "L2FIB evpn mcast leaf info";
    leaf bridge-domain-name {
      xr:xr-xml-map "l2fib:BridgeDomainName";
      type string;
      description "Bridge-domain name";
    }
    leaf bridge-domain-id {
      xr:xr-xml-map "l2fib:BridgeDomainID";
      type uint32;
      description "bdid value";
    }
    leaf is-bound {
      xr:xr-xml-map "l2fib:IsBound";
      type boolean;
      description "Is bound";
    }
  }

  grouping L2FIB-P2MP-PTREE-INFO {
    description "l2fib p2mp ptree info";
    leaf lsm-id-xr {
      xr:xr-xml-map "l2fib:lsm-id-xr";
      type uint32;
      description "MLDP Lsm Id";
    }
    leaf tunnel-id-xr {
      xr:xr-xml-map "l2fib:tunnel-id-xr";
      type uint32;
      description "RSVPTE Tunnel Id";
    }
    leaf p2mp-id-xr {
      xr:xr-xml-map "l2fib:p2mp-id-xr";
      type uint32;
      description "RSVPTE P2MP Id";
    }
    leaf extended-tunnel-id-xr {
      xr:xr-xml-map "l2fib:extended-tunnel-id-xr";
      type inet:ipv4-address;
      description "RSVPTE Ext Tunnel Id";
    }
  }

  grouping L2FIB-PBB-BMAC-SA-INFO {
    description "L2FIB PBB BMAC SA INFO";
    leaf configured {
      xr:xr-xml-map "l2fib:Configured";
      type boolean;
      description "BMAC SA configured";
    }
    leaf mac {
      xr:xr-xml-map "l2fib:MAC";
      type yang:mac-address;
      description "Backbone Source Mac";
    }
    leaf chassis-mac {
      xr:xr-xml-map "l2fib:ChassisMAC";
      type yang:mac-address;
      description "Chassis Mac";
    }
  }

  grouping L2FIB-MCAST-IRB-INFO {
    description "L2FIB MCAST IRB INFO";
    leaf mxid-ac-interface-handle {
      xr:xr-xml-map "l2fib:MxidACInterfaceHandle";
      type xr:Interface-name;
      description "Master XID AC If handle";
    }
    leaf mxid-pw-id {
      xr:xr-xml-map "l2fib:MxidPW_ID";
      type uint32;
      description "Master XID PW ID";
    }
    leaf mxid-next-hop-address {
      xr:xr-xml-map "l2fib:MxidNextHopAddress";
      type inet:ipv4-address;
      description "Master XID NHOP IP Address";
    }
    leaf irb-plat-data-len {
      xr:xr-xml-map "l2fib:IRBPlatDataLen";
      type uint16;
      units "byte";
      description "Platform data bytes";
    }
    leaf-list irb-plat-data {
      xr:xr-xml-map "l2fib:IRBPlatData";
      type uint32;
      max-elements "16";
      description "IRB platform data";
    }
  }

  grouping L2FIB-MCAST-BAG-COUNTERS {
    description "L2FIB mcast statistics counters";
    leaf packets {
      xr:xr-xml-map "l2fib:Packets";
      type uint64;
      description "Number of packets";
    }
    leaf bytes {
      xr:xr-xml-map "l2fib:Bytes";
      type uint64;
      units "byte";
      description "Number of bytes";
    }
  }

  grouping L2FIB-MCAST-STATS-BAG {
    description "L2FIB mcast forwarding statistics";

    container multicast-forward-stat {
      description "forwarded stats";
      uses L2FIB-MCAST-BAG-COUNTERS;
    }

    container received-stat {
      description "received stats";
      uses L2FIB-MCAST-BAG-COUNTERS;
    }

    container punt {
      description "punted stats";
      uses L2FIB-MCAST-BAG-COUNTERS;
    }

    container drop {
      description "dropped stats";
      uses L2FIB-MCAST-BAG-COUNTERS;
    }

    container multicast-core-forward-stat {
      description "core forwarded stats";
      uses L2FIB-MCAST-BAG-COUNTERS;
    }

    container core-received-stat {
      description "core received stats";
      uses L2FIB-MCAST-BAG-COUNTERS;
    }
  }

  grouping L2FIB-PLATFORM-STATS-UNION-BAG {
    description "L2FIB PLATFORM STATS UNION BAG";

    container mulicast {
      when "../data-type = 'mgmt-l2fib-stats-type-mcast'" {
        description "../DataType = 'MGMT_L2FIB_STATS_TYPE_MCAST'";
      }
      description "mulicast";
      uses L2FIB-MCAST-STATS-BAG;
    }
    leaf data-type {
      xr:xr-xml-map "l2fib:DataType";
      type Mgmt-l2fib-stats-data;
      description "DataType";
    }
  }

  grouping L2FIB-PLATFORM-STATS-BAG {
    description "L2FIB platform statistics";

    container forward-stat {
      description "fwd stats";
      uses L2FIB-PLATFORM-STATS-UNION-BAG;
    }
  }

  grouping L2FIB-PREFIX-INFO {
    description "L2FIB PREFIX INFO";
    leaf proto {
      xr:xr-xml-map "l2fib:Proto";
      type uint8;
      description "The prefix protocol";
    }
    leaf prefix-length {
      xr:xr-xml-map "l2fib:PrefixLength";
      type uint16;
      description "The prefix length";
    }
    leaf prefix {
      xr:xr-xml-map "l2fib:prefix";
      type yang:hex-string;
      description "The prefix";
    }
  }

  grouping L2FIB-MCAST-LEAF-INFO {
    description "l2fib mcast leaf info";

    container multicast-base-information {
      description "Base Information";
      uses L2FIB-BASE-INFO;
    }

    container source-prefix {
      description "Source Prefix";
      uses L2FIB-PREFIX-INFO;
    }

    container destination-prefix {
      description "Destination Prefix";
      uses L2FIB-PREFIX-INFO;
    }

    container forward-stats {
      description "Forwarding Statistics";
      uses L2FIB-PLATFORM-STATS-BAG;
    }

    container irb-info {
      description "IRB Information";
      uses L2FIB-MCAST-IRB-INFO;
    }
    leaf bridge-id {
      xr:xr-xml-map "l2fib:BridgeID";
      type uint32;
      description "Bridge ID";
    }
    leaf xid-count {
      xr:xr-xml-map "l2fib:XIDCount";
      type uint16;
      description "Count of XIDs";
    }
    leaf platform-data-length {
      xr:xr-xml-map "l2fib:PlatformDataLength";
      type uint8;
      description "The mcast platform data len";
    }
    leaf platform-data {
      xr:xr-xml-map "l2fib:PlatformData";
      type yang:hex-string;
      description "The mcast platform data";
    }
    leaf hardware-information {
      xr:xr-xml-map "l2fib:HardwareInformation";
      type yang:hex-string;
      description "Platform Hardware info";
    }
    leaf bridge-domain-name {
      xr:xr-xml-map "l2fib:BridgeDomainName";
      type string {
        length "0..66";
      }
      description "Bridge Name";
    }
  }

  grouping L2FIB-GBL-RTD-ITEM {
    description "Round-trip delay for PD calls per action";
    leaf number-pd-update {
      xr:xr-xml-map "l2fib:NumberPDUpdate";
      type uint32;
      description "The number of time PD is called";
    }
    leaf number-pd-update-zero {
      xr:xr-xml-map "l2fib:NumberPDUpdateZero";
      type uint32;
      description "The number of time PD is called in 0 time";
    }
    leaf minimum-round-trip-delay {
      xr:xr-xml-map "l2fib:MinimumRoundTripDelay";
      type uint64;
      description "The minimum round trip delay";
    }
    leaf maximum-round-trip-delay {
      xr:xr-xml-map "l2fib:MaximumRoundTripDelay";
      type uint64;
      description "The maximum round trip delay";
    }
    leaf average-round-trip-delay {
      xr:xr-xml-map "l2fib:AverageRoundTripDelay";
      type uint64;
      description "The average round trip delay";
    }
  }

  grouping L2FIB-GBL-RTD {
    description "Round-trip delay measurement";

    container bdxc-rtd {
      description "bdxc rtd";
      uses L2FIB-GBL-RTD-ITEM;
    }

    container aging-rtd {
      description "aging rtd";
      uses L2FIB-GBL-RTD-ITEM;
    }

    container punt-rtd {
      description "punt rtd";
      uses L2FIB-GBL-RTD-ITEM;
    }

    container lock-rtd {
      description "lock rtd";
      uses L2FIB-GBL-RTD-ITEM;
    }

    container platform-init-rtd {
      description "platform init rtd";
      uses L2FIB-GBL-RTD-ITEM;
    }
    leaf rtd-max-obj-type {
      xr:xr-xml-map "l2fib:RTD_MAX_OBJTYPE";
      type uint32;
      description "RTD MAX OBJTYPE";
    }

    list create {
      max-elements "51";
      description "create";
      uses L2FIB-GBL-RTD-ITEM;
    }

    list modify {
      max-elements "51";
      description "modify";
      uses L2FIB-GBL-RTD-ITEM;
    }

    list delete {
      max-elements "51";
      description "delete";
      uses L2FIB-GBL-RTD-ITEM;
    }

    list bind {
      max-elements "51";
      description "bind";
      uses L2FIB-GBL-RTD-ITEM;
    }

    list unbind {
      max-elements "51";
      description "unbind";
      uses L2FIB-GBL-RTD-ITEM;
    }

    list mac-flush {
      max-elements "51";
      description "mac flush";
      uses L2FIB-GBL-RTD-ITEM;
    }

    list pirtd {
      max-elements "51";
      description "pirtd";
      uses L2FIB-GBL-RTD-ITEM;
    }
  }

  grouping L2FIB-EVT-ENTRY {
    description "L2FIB event item";
    leaf event-time {
      xr:xr-xml-map "l2fib:EventTime";
      type string {
        length "0..32";
      }
      description "The real timestamp of the event";
    }
    leaf event-type {
      xr:xr-xml-map "l2fib:EventType";
      type uint8;
      description "Event type";
    }
    leaf event-many {
      xr:xr-xml-map "l2fib:EventMany";
      type boolean;
      description "Multiple event instance flag";
    }
    leaf event-sticky {
      xr:xr-xml-map "l2fib:EventSticky";
      type boolean;
      description "Unwrittable flag";
    }
    leaf event-flags {
      xr:xr-xml-map "l2fib:EventFlags";
      type uint32;
      description "base flag object";
    }
  }

  grouping L2FIB-GBL-EVT-HISTORY {
    description "L2FIB global event history";
    leaf event-neighbor-entry {
      xr:xr-xml-map "l2fib:EventNeighborEntry";
      type uint16;
      description "number of item in the array";
    }
    leaf-list extra-information1 {
      xr:xr-xml-map "l2fib:ExtraInformation1";
      type uint32;
      max-elements "256";
      description "extra information1";
    }
    leaf-list extra-information2 {
      xr:xr-xml-map "l2fib:ExtraInformation2";
      type uint32;
      max-elements "256";
      description "extra information2";
    }

    list event-entry {
      max-elements "256";
      description "event entry";
      uses L2FIB-EVT-ENTRY;
    }
  }

  grouping L2FIB-EXT-MSG-SUMMARY-INFO {
    description "L2FIB message counters summary info";

    container event-history {
      description "Event history buffer";
      uses L2FIB-GBL-EVT-HISTORY;
    }

    container round-trip-delay {
      description "Round-Trip delay";
      uses L2FIB-GBL-RTD;
    }

    list message {
      max-elements "85";
      description "message";
      uses L2FIB-GBL-MSG-INFO;
    }
  }

  grouping L2FIB-GBL-MSG-INFO {
    description "L2FIB message counter item info";
    leaf messgae-count {
      xr:xr-xml-map "l2fib:MessgaeCount";
      type uint32;
      description "number of message";
    }
    leaf time {
      xr:xr-xml-map "l2fib:Time";
      type string {
        length "0..32";
      }
      description "Time string";
    }
    leaf information1 {
      xr:xr-xml-map "l2fib:Information1";
      type uint32;
      description "Extra info 1";
    }
    leaf information2 {
      xr:xr-xml-map "l2fib:Information2";
      type uint32;
      description "Extra info 2";
    }
  }

  grouping L2FIB-MCAST-SUMMARY-INFO {
    description "l2fib mcast summary info";
    leaf bridge-domain-name {
      xr:xr-xml-map "l2fib:BridgeDomainName";
      type string {
        length "0..66";
      }
      description "Bridge Name";
    }
    leaf bridge-domain-id {
      xr:xr-xml-map "l2fib:BridgeDomainID";
      type uint32;
      description "Bridge ID";
    }
    leaf multicast-update {
      xr:xr-xml-map "l2fib:MulticastUpdate";
      type uint32;
      description "Multicast Updates";
    }
    leaf multicast-update-dropped {
      xr:xr-xml-map "l2fib:MulticastUpdateDropped";
      type uint32;
      description "Multicast Updates";
    }
    leaf number-of-routes {
      xr:xr-xml-map "l2fib:NumberOfRoutes";
      type uint32;
      description "Number of Routes";
    }
    leaf number-of-mroute-add {
      xr:xr-xml-map "l2fib:NumberOfMrouteAdd";
      type uint32;
      description "Number of Mroutes Added";
    }
    leaf number-mroute-deleted {
      xr:xr-xml-map "l2fib:NumberMrouteDeleted";
      type uint32;
      description "Number of Mroutes Deleted";
    }
    leaf number-mroutes-deleted-all {
      xr:xr-xml-map "l2fib:NumberMroutesDeletedAll";
      type uint32;
      description "Number of Mroutes All Deleted";
    }
    leaf number-mroute-delete-drop {
      xr:xr-xml-map "l2fib:NumberMrouteDeleteDrop";
      type uint32;
      description "Number of Mroutes Delete droped";
    }
    leaf number-mroute-all-delete-drop {
      xr:xr-xml-map "l2fib:NumberMrouteAllDeleteDrop";
      type uint32;
      description "Number of Mroutes All Delete droped";
    }
    leaf number-xid-add {
      xr:xr-xml-map "l2fib:NumberXIDAdd";
      type uint32;
      description "Number of XID Added";
    }
    leaf number-xid-deleted {
      xr:xr-xml-map "l2fib:NumberXIDDeleted";
      type uint32;
      description "Number of XID Deleted";
    }
    leaf number-of-xid {
      xr:xr-xml-map "l2fib:NumberOfXID";
      type uint32;
      description "Number of XIDs";
    }
    leaf stale-deleted {
      xr:xr-xml-map "l2fib:StaleDeleted";
      type uint32;
      description "Stale Deleted";
    }
    leaf stale-xid-deleted {
      xr:xr-xml-map "l2fib:StaleXIDDeleted";
      type uint32;
      description "Stale XID Deleted";
    }

    list message {
      max-elements "14";
      description "Global Message Information";
      uses L2FIB-GBL-MSG-INFO;
    }
  }

  grouping L2FIB-FXS-INFO {
    description "L2VPN FXS info";

    container base {
      description "Base Information";
      uses L2FIB-BASE-INFO;
    }
    leaf fxs-id {
      xr:xr-xml-map "l2fib:FXS_ID";
      type uint32;
      description "FXS ID";
    }
    leaf segment-type {
      xr:xr-xml-map "l2fib:SegmentType";
      type uint8;
      description "Segment type";
    }
  }

  grouping L2FIB-BRIDGE-PORT-P2MP-INFO {
    description "L2FIB BRIDGE PORT P2MP INFO";
    leaf ptree-type {
      xr:xr-xml-map "l2fib:PTreeType";
      type L2vpn-ptree;
      description "P2MP ptree type";
    }
    leaf lsm-id {
      xr:xr-xml-map "l2fib:LSM_ID";
      type uint32;
      description "MLDP LSM id";
    }
    leaf tunnel-id {
      xr:xr-xml-map "l2fib:TunnelID";
      type uint16;
      description "TE Tunnel Id";
    }
    leaf p2mp-id {
      xr:xr-xml-map "l2fib:P2MP_ID";
      type uint16;
      description "TE P2MP Id";
    }
    leaf extended-tunnel-id {
      xr:xr-xml-map "l2fib:ExtendedTunnelID";
      type inet:ipv4-address;
      description "TE Extended Tunnel Id";
    }
    leaf ptree-owner-lmrib {
      xr:xr-xml-map "l2fib:PTreeOwnerLMRIB";
      type boolean;
      description "PTree Owner LMRIB";
    }
  }

  grouping L2FIB-PROFILE-INFO {
    description "L2VPN feature profile information";
    leaf profile-name {
      xr:xr-xml-map "l2fib:ProfileName";
      type string;
      description "Feature profile name";
    }
  }

  grouping L2FIB-FEATURE-UN {
    description "L2FIB FEATURE UN";

    container dhcp {
      when "../feature-type = 'l2fib-feature-dhcp-snooping'" {
        description
          "../feature_type = 'L2FIB_FEATURE_DHCP_SNOOPING'";
      }
      description "dhcp";
      uses L2FIB-PROFILE-INFO;
    }

    container igmp {
      when "../feature-type = 'l2fib-feature-igmp-snooping'" {
        description
          "../feature_type = 'L2FIB_FEATURE_IGMP_SNOOPING'";
      }
      description "igmp";
      uses L2FIB-PROFILE-INFO;
    }

    container mld {
      when "../feature-type = 'l2fib-feature-mld-snooping'" {
        description
          "../feature_type = 'L2FIB_FEATURE_MLD_SNOOPING'";
      }
      description "mld";
      uses L2FIB-PROFILE-INFO;
    }
    leaf feature-type {
      xr:xr-xml-map "l2fib:feature_type";
      type L2fib-feature;
      description "feature type";
    }
  }

  grouping L2FIB-OPER-INFO {
    description "L2VPN common operational information";
    leaf mtu {
      xr:xr-xml-map "l2fib:MTU";
      type uint32;
      description "MTU";
    }
    leaf mac-aging-time {
      xr:xr-xml-map "l2fib:MACAgingTime";
      type uint32;
      units "minute";
      description "MAC aging time in minutes";
    }
    leaf mac-limit {
      xr:xr-xml-map "l2fib:MACLimit";
      type uint32;
      description "MAC limit";
    }
    leaf number-of-macs {
      xr:xr-xml-map "l2fib:numberOfMacs";
      type uint32;
      description "numberOfMacs";
    }
    leaf admin-disabled {
      xr:xr-xml-map "l2fib:AdminDisabled";
      type boolean;
      description "Is administratively disabled";
    }
    leaf flooding-disabled {
      xr:xr-xml-map "l2fib:FloodingDisabled";
      type boolean;
      description "Is flooding disabled";
    }
    leaf flood-unknown-unicast-enabled {
      xr:xr-xml-map "l2fib:FloodUnknownUnicastEnabled";
      type boolean;
      description "Is flooding unknown unicast disabled";
    }
    leaf mac-limit-action {
      xr:xr-xml-map "l2fib:MACLimitAction";
      type Mgmt-l2fib-mac-limit-action;
      description "MAC limit action";
    }
    leaf mac-learning-disabled {
      xr:xr-xml-map "l2fib:MACLearningDisabled";
      type boolean;
      description "Is MAC learning disabled";
    }
    leaf mac-port-down-flush-disabled {
      xr:xr-xml-map "l2fib:MACPortDownFlushDisabled";
      type boolean;
      description "Is MAC port down flush disabled";
    }
    leaf mac-limit-notification-type {
      xr:xr-xml-map "l2fib:MACLimitNotificationType";
      type Mgmt-l2fib-mac-limit-notify;
      description "MAC limit notification";
    }
    leaf is-mac-secure-enabled {
      xr:xr-xml-map "l2fib:IsMACSecureEnabled";
      type boolean;
      description "Is MAC Secure Enabled";
    }
    leaf is-mac-secure-logging-enabled {
      xr:xr-xml-map "l2fib:IsMACSecureLoggingEnabled";
      type boolean;
      description "Is MAC Secure Logging Enabled";
    }
    leaf mac-secure-action {
      xr:xr-xml-map "l2fib:MACSecureAction";
      type Mgmt-l2fib-mac-sec-action;
      description "MAC secure action";
    }
    leaf is-mac-secure-accept-shutdown {
      xr:xr-xml-map "l2fib:IsMACSecureAcceptShutdown";
      type boolean;
      description "Is MAC secure accept shutdown (BP only)";
    }
    leaf mac-aging-type {
      xr:xr-xml-map "l2fib:MACAgingType";
      type boolean;
      description "MAC aging type";
    }
    leaf storm-control-unicast-enabled {
      xr:xr-xml-map "l2fib:StormControlUnicastEnabled";
      type boolean;
      description "Is unicast storm control enabled";
    }
    leaf storm-control-broadcast-enabled {
      xr:xr-xml-map "l2fib:StormControlBroadcastEnabled";
      type boolean;
      description "Is broadcast storm control enabled";
    }
    leaf storm-control-multicast-enabled {
      xr:xr-xml-map "l2fib:StormControlMulticastEnabled";
      type boolean;
      description "Is multicast storm control enabled";
    }
    leaf storm-control-unicast-rate-unit {
      xr:xr-xml-map "l2fib:StormControlUnicastRateUnit";
      type L2fib-storm-control-rate-unit;
      description "Storm control unicast rate unit";
    }
    leaf storm-control-broadcast-rate-unit {
      xr:xr-xml-map "l2fib:StormControlBroadcastRateUnit";
      type L2fib-storm-control-rate-unit;
      description "Storm control broadcast rate unit";
    }
    leaf storm-control-multicast-rate-unit {
      xr:xr-xml-map "l2fib:StormControlMulticastRateUnit";
      type L2fib-storm-control-rate-unit;
      description "Storm control multicast rate unit";
    }
    leaf dhcp-enabled {
      xr:xr-xml-map "l2fib:DHCPEnabled";
      type boolean;
      description "Is DHCP snooping enabled";
    }
    leaf dhcp-trusted {
      xr:xr-xml-map "l2fib:DHCPTrusted";
      type boolean;
      description "Is DHCP trusted";
    }
    leaf is-dai-enabled {
      xr:xr-xml-map "l2fib:IsDAIEnabled";
      type boolean;
      description "Is Dynamic ARP Inspection Enabled";
    }
    leaf is-dai-addr-validation-ipv4-enabled {
      xr:xr-xml-map "l2fib:IsDAIAddrValidationIPv4Enabled";
      type boolean;
      description "Is DAI IPv4 Address Validation Enabled";
    }
    leaf is-dai-addr-validation-source-mac-enabled {
      xr:xr-xml-map "l2fib:IsDAIAddrValidationSourceMACEnabled";
      type boolean;
      description "Is DAI Source MAC Address Validation Enabled";
    }
    leaf is-dai-addr-validation-destination-mac-enabled {
      xr:xr-xml-map "l2fib:IsDAIAddrValidationDestinationMACEnabled";
      type boolean;
      description "Is DAI Destination MAC Validation enabled";
    }
    leaf is-dai-logging-enabled {
      xr:xr-xml-map "l2fib:IsDAILoggingEnabled";
      type boolean;
      description "Is DAI Logging Enabled";
    }
    leaf is-ipsg-enabled {
      xr:xr-xml-map "l2fib:IsIPSGEnabled";
      type boolean;
      description "Is IP Source Guard Enabled";
    }
    leaf is-ipsg-logging-enabled {
      xr:xr-xml-map "l2fib:IsIPSGLoggingEnabled";
      type boolean;
      description "Is IP Source Guard Logging Enabled";
    }
    leaf is-vpls-flood-optimization-enabled {
      xr:xr-xml-map "l2fib:IsVplsFloodOptimizationEnabled";
      type boolean;
      description "Is MMRP  Flood Optimization Enabled";
    }
    leaf igmp-snoop-enabled {
      xr:xr-xml-map "l2fib:IGMPSnoopEnabled";
      type boolean;
      description "Is IGMP snooping enabled";
    }
    leaf igmp-snoop-profile-enabled {
      xr:xr-xml-map "l2fib:IGMPSnoopProfileEnabled";
      type boolean;
      description "Is IGMP snooping profile enabled";
    }
    leaf igmp-flood-forward-enabled {
      xr:xr-xml-map "l2fib:IGMPFloodForwardEnabled";
      type boolean;
      description "Is IGMP flood forwarding enabled";
    }
    leaf igmp-mroute-port-enabled {
      xr:xr-xml-map "l2fib:IGMPMroutePortEnabled";
      type boolean;
      description "Is mrouter port";
    }
    leaf igmp-route-guard-enabled {
      xr:xr-xml-map "l2fib:IGMPRouteGuardEnabled";
      type boolean;
      description "Is router gurad enabled";
    }
    leaf mld-snoop-enabled {
      xr:xr-xml-map "l2fib:MLDSnoopEnabled";
      type boolean;
      description "Is MLD snooping enabled";
    }
    leaf mld-snoop-profile-enabled {
      xr:xr-xml-map "l2fib:MLDSnoopProfileEnabled";
      type boolean;
      description "Is MLD snooping profile enabled";
    }
    leaf mld-flood-forward-enabled {
      xr:xr-xml-map "l2fib:MLDFloodForwardEnabled";
      type boolean;
      description "Is MLD flood forwarding enabled";
    }
    leaf mld-mroute-port-enabled {
      xr:xr-xml-map "l2fib:MLDMroutePortEnabled";
      type boolean;
      description "Is mrouter port";
    }
    leaf mld-route-guard-enabled {
      xr:xr-xml-map "l2fib:MLDRouteGuardEnabled";
      type boolean;
      description "Is router gurad enabled";
    }
    leaf stp-participating {
      xr:xr-xml-map "l2fib:STPParticipating";
      type boolean;
      description "Is Spanning Tree Protocol participating";
    }
    leaf bvi-configured {
      xr:xr-xml-map "l2fib:BVIConfigured";
      type boolean;
      description "Is BVI Interface configured";
    }
    leaf is-bvi-up {
      xr:xr-xml-map "l2fib:IsBVIUp";
      type boolean;
      description "Is BVI state UP";
    }
    leaf is-vni-enabled {
      xr:xr-xml-map "l2fib:IsVNIEnabled";
      type boolean;
      description "Is VNI enabled";
    }
    leaf is-evpn-enabled {
      xr:xr-xml-map "l2fib:IsEVPNEnabled";
      type boolean;
      description "Is EVPN enabled";
    }
    leaf is-pbbevpn-enabled {
      xr:xr-xml-map "l2fib:IsPBBEVPNEnabled";
      type boolean;
      description "Is PBBEVPN enabled";
    }
    leaf msti {
      xr:xr-xml-map "l2fib:MSTI";
      type uint32;
      description "Multi-spanning tree instance";
    }
    leaf is-p2mp-pw-enabled {
      xr:xr-xml-map "l2fib:IsP2MP_PWEnabled";
      type boolean;
      description "Is P2MP PW enabled";
    }
    leaf is-igmp-snoop-enabled {
      xr:xr-xml-map "l2fib:IsIGMPSnoopEnabled";
      type boolean;
      description "Is IGMP Snooping admin enabled";
    }
    leaf nv-satellite-offload-ipv4-multicast-disabled {
      xr:xr-xml-map "l2fib:nVSatelliteOffloadIPv4MulticastDisabled";
      type boolean;
      description "nV Satellite Offload IPv4 Multicast Disabled";
    }

    list feature {
      description "Feature information";
      uses L2FIB-FEATURE-UN;
    }
  }

  grouping L2FIB-OPER-BRIDGE-PORT-INFO {
    description "L2VPN bridge port operational information";

    container operational-information {
      description "L2 operational information";
      uses L2FIB-OPER-INFO;
    }
    leaf unicast-storm-control-pps {
      xr:xr-xml-map "l2fib:UnicastStormControlPPS";
      type uint64;
      description "Unicast storm control pps";
    }
    leaf unicast-storm-control-kb-ps {
      xr:xr-xml-map "l2fib:UnicastStormControlKbPS";
      type uint64;
      units "kbit/s";
      description "Unicast storm control kbps";
    }
    leaf broadcast-storm-control-pps {
      xr:xr-xml-map "l2fib:BroadcastStormControlPPS";
      type uint64;
      description "Broadcast storm control pps";
    }
    leaf broadcast-storm-control-kb-ps {
      xr:xr-xml-map "l2fib:BroadcastStormControlKbPS";
      type uint64;
      units "kbit/s";
      description "Broadcast storm control kbps";
    }
    leaf multicast-storm-control-pps {
      xr:xr-xml-map "l2fib:MulticastStormControlPPS";
      type uint64;
      description "Multicast storm control pps";
    }
    leaf multicast-storm-control-kb-ps {
      xr:xr-xml-map "l2fib:MulticastStormControlKbPS";
      type uint64;
      units "kbit/s";
      description "Multicast storm control kbps";
    }
  }

  grouping L2FIB-BRIDGE-PORT-INFO {
    description "L2VPN bridge port info";

    container base {
      description "Base Information";
      uses L2FIB-BASE-INFO;
    }

    container oper {
      description "Operational information";
      uses L2FIB-OPER-BRIDGE-PORT-INFO;
    }

    container p2mp {
      description "BP P2MP PW Information";
      uses L2FIB-BRIDGE-PORT-P2MP-INFO;
    }
    leaf bridge-id {
      xr:xr-xml-map "l2fib:BridgeID";
      type uint32;
      description "Bridge ID";
    }
    leaf shg-id {
      xr:xr-xml-map "l2fib:SHG_ID";
      type uint32;
      description "Split horizon group ID";
    }
    leaf msti-pointer {
      xr:xr-xml-map "l2fib:MSTIPointer";
      type uint32;
      description "MSTI Pointer";
    }
    leaf segment-type {
      xr:xr-xml-map "l2fib:SegmentType";
      type uint8;
      description "Segment type";
    }
    leaf mvrp-sequence-number {
      xr:xr-xml-map "l2fib:MVRPSequenceNumber";
      type uint16;
      description "MVRP Sequence Number";
    }
    leaf learn-key {
      xr:xr-xml-map "l2fib:LearnKey";
      type uint8;
      description "Learn Key";
    }
  }

  grouping L2FIB-SEG2-UN {
    description "L2FIB SEG2 UN";

    container ac {
      when "../data-type = 'mgmt-l2fib-data-type-ac'" {
        description "../DataType = 'MGMT_L2FIB_DATA_TYPE_AC'";
      }
      description "ac";
      uses L2FIB-AC-INFO;
    }

    container bp {
      when "../data-type = 'mgmt-l2fib-data-type-bridge-port'" {
        description
          "../DataType =
          'MGMT_L2FIB_DATA_TYPE_BRIDGE_PORT'";
      }
      description "bp";
      uses L2FIB-BRIDGE-PORT-INFO;
    }

    container fxs {
      when "../data-type = 'mgmt-l2fib-data-type-fxs'" {
        description "../DataType = 'MGMT_L2FIB_DATA_TYPE_FXS'";
      }
      description "fxs";
      uses L2FIB-FXS-INFO;
    }

    container pw {
      when "../data-type != 'mgmt-l2fib-data-type-ac' and"+
        " ../data-type != 'mgmt-l2fib-data-type-bridge-port' and"+
        " ../data-type != 'mgmt-l2fib-data-type-fxs'" {
          description
            "../DataType != 'MGMT_L2FIB_DATA_TYPE_AC' and .
            ./DataType !=
            'MGMT_L2FIB_DATA_TYPE_BRIDGE_PORT' and .
            ./DataType != 'MGMT_L2FIB_DATA_TYPE_FXS'";
      }
      description "pw";
      uses L2FIB-PW-INFO;
    }
    leaf data-type {
      xr:xr-xml-map "l2fib:DataType";
      type Mgmt-l2fib-data;
      description "DataType";
    }
  }

  grouping L2FIB-BACKUP-PW-INFO {
    description "L2FIB BACKUP PW INFO";

    container atom {
      description "atom";
      uses L2FIB-PW-MPLS-INFO;
    }
    leaf backup-next-hop {
      xr:xr-xml-map "l2fib:BackupNextHop";
      type inet:ipv4-address;
      description "Backup Next Hop";
    }
    leaf backup-pseudo-wire-id-type {
      xr:xr-xml-map "l2fib:BackupPseudoWireIDType";
      type L2fib-pw-id;
      description "Pseudowire ID type";
    }
    leaf backup-pseudo-wire-id {
      xr:xr-xml-map "l2fib:BackupPseudoWireID";
      type uint32;
      description "Backup Pseudowire ID";
    }
    leaf redundancy-role {
      xr:xr-xml-map "l2fib:RedundancyRole";
      type L2fib-pw-redundancy-role;
      description "Redundancy Role";
    }
    leaf active {
      xr:xr-xml-map "l2fib:Active";
      type boolean;
      description "PW is active and forwarding";
    }
    leaf bound {
      xr:xr-xml-map "l2fib:Bound";
      type boolean;
      description "Bound";
    }
    leaf pw-flow-label-tx {
      xr:xr-xml-map "l2fib:PWFlowLabelTX";
      type boolean;
      description "Pseudowire flow label TX enabled";
    }
    leaf grouping-supported {
      xr:xr-xml-map "l2fib:GroupingSupported";
      type boolean;
      description "Grouping supported";
    }
    leaf group-id {
      xr:xr-xml-map "l2fib:GroupID";
      type uint32;
      description "PW Group Id";
    }
    leaf group-state {
      xr:xr-xml-map "l2fib:GroupState";
      type L2fib-group-state;
      description "Group State";
    }
  }

  grouping L2FIB-PW-L2TP-IPV6-TS-SESS-INFO {
    description "L2FIB PW L2TP IPV6 TS SESS INFO";
    leaf cookie-size {
      xr:xr-xml-map "l2fib:CookieSize";
      type uint8;
      description "Cookie size";
    }
    leaf cookie-low-value {
      xr:xr-xml-map "l2fib:CookieLowValue";
      type uint32;
      description "Cookie low value";
    }
    leaf cookie-high-value {
      xr:xr-xml-map "l2fib:CookieHighValue";
      type uint32;
      description "Cookie high value";
    }
    leaf secondary-cookie-size {
      xr:xr-xml-map "l2fib:SecondaryCookieSize";
      type uint8;
      description "Secondary Cookie size";
    }
    leaf secondary-cookie-low-value {
      xr:xr-xml-map "l2fib:SecondaryCookieLowValue";
      type uint32;
      description "Secondary Cookie low value";
    }
    leaf secondary-cookie-high-value {
      xr:xr-xml-map "l2fib:SecondaryCookieHighValue";
      type uint32;
      description "Secondary Cookie high value";
    }
    leaf session-id {
      xr:xr-xml-map "l2fib:SessionID";
      type uint32;
      description "L2TP session ID";
    }
  }

  grouping L2FIB-PW-L2TP-IPV6-TS-INFO {
    description "L2FIB PW L2TP IPV6 TS INFO";

    container local {
      description "Local session info";
      uses L2FIB-PW-L2TP-IPV6-TS-SESS-INFO;
    }

    container remote {
      description "Remote session info";
      uses L2FIB-PW-L2TP-SESS-INFO;
    }
    leaf tos-val {
      xr:xr-xml-map "l2fib:TOSVal";
      type uint8;
      description "TOS val";
    }
    leaf ttl {
      xr:xr-xml-map "l2fib:TTL";
      type uint8;
      description "TTL";
    }
    leaf path-mtu {
      xr:xr-xml-map "l2fib:PathMTU";
      type uint16;
      description "Path MTU";
    }
    leaf sequence-number-sent {
      xr:xr-xml-map "l2fib:SequenceNumberSent";
      type uint32;
      description "Number of sequence sent";
    }
    leaf sequence-number-expected {
      xr:xr-xml-map "l2fib:SequenceNumberExpected";
      type uint32;
      description "Number of sequence expected";
    }
    leaf local-address {
      xr:xr-xml-map "l2fib:LocalAddress";
      type inet:ipv6-address;
      description "Local address";
    }
    leaf remote-address {
      xr:xr-xml-map "l2fib:RemoteAddress";
      type inet:ipv6-address;
      description "Remote address";
    }
  }

  grouping L2FIB-PW-L2TPV2-SESS-INFO {
    description "L2FIB PW L2TPV2 SESS INFO";
    leaf session-id {
      xr:xr-xml-map "l2fib:SessionID";
      type uint32;
      description "L2TPv2 session ID";
    }
    leaf tunnel-id {
      xr:xr-xml-map "l2fib:TunnelID";
      type uint32;
      description "L2TPv2 tunnel ID";
    }
  }

  grouping L2FIB-PW-L2TPV2-INFO {
    description "L2FIB PW L2TPV2 INFO";

    container local {
      description "Local session info";
      uses L2FIB-PW-L2TPV2-SESS-INFO;
    }

    container remote {
      description "Remote session info";
      uses L2FIB-PW-L2TPV2-SESS-INFO;
    }
    leaf pw-flags {
      xr:xr-xml-map "l2fib:PWFlags";
      type uint8;
      description "L2TPv2 PW flags";
    }
    leaf tos-val {
      xr:xr-xml-map "l2fib:TOSVal";
      type uint8;
      description "TOS val";
    }
    leaf ttl {
      xr:xr-xml-map "l2fib:TTL";
      type uint8;
      description "TTL [Hops number]";
    }
    leaf path-mtu {
      xr:xr-xml-map "l2fib:PathMTU";
      type uint16;
      units "byte";
      description "Path MTU [Bytes]";
    }
    leaf protocol {
      xr:xr-xml-map "l2fib:Protocol";
      type uint16;
      description "Protocol [UDP RFC-768]";
    }
    leaf rem-udp-port {
      xr:xr-xml-map "l2fib:RemUDPPort";
      type uint16;
      description "Remote UDP Port";
    }
    leaf xconnect-id {
      xr:xr-xml-map "l2fib:XConnectID";
      type uint32;
      description "Xconnect ID";
    }
    leaf next-hop-address {
      xr:xr-xml-map "l2fib:NextHopAddress";
      type inet:ipv4-address;
      description "Next Hop Address";
    }
    leaf source-address {
      xr:xr-xml-map "l2fib:SourceAddress";
      type inet:ipv4-address;
      description "Source Address";
    }
  }

  grouping L2FIB-PW-L2TP-SESS-INFO {
    description "L2FIB PW L2TP SESS INFO";
    leaf session-id {
      xr:xr-xml-map "l2fib:SessionID";
      type uint32;
      description "L2TP session ID";
    }
    leaf cookie-size {
      xr:xr-xml-map "l2fib:CookieSize";
      type uint8;
      description "Cookie size";
    }
    leaf cookie-low-value {
      xr:xr-xml-map "l2fib:CookieLowValue";
      type uint32;
      description "Cookie low value";
    }
    leaf cookie-high-value {
      xr:xr-xml-map "l2fib:CookieHighValue";
      type uint32;
      description "Cookie high value";
    }
  }

  grouping L2FIB-PW-L2TP-INFO {
    description "L2FIB PW L2TP INFO";

    container local {
      description "Local session info";
      uses L2FIB-PW-L2TP-SESS-INFO;
    }

    container remote {
      description "Remote session info";
      uses L2FIB-PW-L2TP-SESS-INFO;
    }
    leaf tos-val {
      xr:xr-xml-map "l2fib:TOSVal";
      type uint8;
      description "TOS val";
    }
    leaf ttl {
      xr:xr-xml-map "l2fib:TTL";
      type uint8;
      description "TTL";
    }
    leaf path-mtu {
      xr:xr-xml-map "l2fib:PathMTU";
      type uint16;
      description "Path MTU";
    }
    leaf sequence-number-sent {
      xr:xr-xml-map "l2fib:SequenceNumberSent";
      type uint32;
      description "Number of sequence sent";
    }
    leaf sequence-number-expected {
      xr:xr-xml-map "l2fib:SequenceNumberExpected";
      type uint32;
      description "Number of sequence expected";
    }
  }

  grouping L2FIB-PW-MPLS-INFO {
    description "L2FIB PW MPLS INFO";
    leaf pw-label {
      xr:xr-xml-map "l2fib:PWLabel";
      type uint32;
      description "PW Label";
    }
    leaf pw-local-label {
      xr:xr-xml-map "l2fib:PWLocalLabel";
      type uint32;
      description "Local PW Label";
    }
    leaf pw-tunnel-interface {
      xr:xr-xml-map "l2fib:PWTunnelInterface";
      type uint32;
      description "PW tunnel interface";
    }
    leaf pw-xcid {
      xr:xr-xml-map "l2fib:PWXcid";
      type uint32;
      description "PW XCID";
    }
  }

  grouping L2FIB-PW-UN {
    description "L2FIB PW UN";

    container mpls {
      when "../data-type = 'mgmt-l2fib-data-type-atom'" {
        description "../DataType = 'MGMT_L2FIB_DATA_TYPE_ATOM'";
      }
      description "mpls";
      uses L2FIB-PW-MPLS-INFO;
    }

    container l2tp {
      when "../data-type = 'mgmt-l2fib-data-type-l2tp'" {
        description "../DataType = 'MGMT_L2FIB_DATA_TYPE_L2TP'";
      }
      description "l2tp";
      uses L2FIB-PW-L2TP-INFO;
    }

    container l2tpv2 {
      when "../data-type = 'mgmt-l2fib-data-type-l2tpv2'" {
        description "../DataType = 'MGMT_L2FIB_DATA_TYPE_L2TPV2'";
      }
      description "l2tpv2";
      uses L2FIB-PW-L2TPV2-INFO;
    }

    container l2tp-ipv6-ts {
      when "../data-type = 'mgmt-l2fib-data-type-l2tp-ipv6-ts'" {
        description
          "../DataType =
          'MGMT_L2FIB_DATA_TYPE_L2TP_IPV6_TS'";
      }
      description "l2tp ipv6 ts";
      uses L2FIB-PW-L2TP-IPV6-TS-INFO;
    }
    leaf data-type {
      xr:xr-xml-map "l2fib:DataType";
      type Mgmt-l2fib-data;
      description "DataType";
    }
  }

  grouping L2FIB-NHOP-INFO {
    description "L2FIB NHOP INFO";

    container base {
      description "Base Information";
      uses L2FIB-BASE-INFO;
    }
    leaf next-hop-address {
      xr:xr-xml-map "l2fib:NextHopAddress";
      type inet:ipv4-address;
      description "NHOP Address";
    }
    leaf plaformt-data-valid {
      xr:xr-xml-map "l2fib:PlaformtDataValid";
      type boolean;
      description "Is Platform Data Valid";
    }
    leaf platform-data-length {
      xr:xr-xml-map "l2fib:PlatformDataLength";
      type uint32;
      description "Platform Data Length";
    }
    leaf children-count {
      xr:xr-xml-map "l2fib:ChildrenCount";
      type uint32;
      description "Children Count";
    }
  }

  grouping L2FIB-PW-INFO {
    description "L2FIB PW INFO";

    container base {
      description "Base Information";
      uses L2FIB-BASE-INFO;
    }

    container next-hop {
      description "Next Hop";
      uses L2FIB-NHOP-INFO;
    }

    container pseudo-wire-union {
      description "Union of MPLS or L2TP";
      uses L2FIB-PW-UN;
    }

    container backup-pseudo-wire {
      description "Backup Pseudowire";
      uses L2FIB-BACKUP-PW-INFO;
    }
    leaf pw-id {
      xr:xr-xml-map "l2fib:PW_ID";
      type uint64;
      description "Pseudowire ID";
    }
    leaf signal-capability-flags {
      xr:xr-xml-map "l2fib:SignalCapabilityFlags";
      type uint32;
      description "Sig Capability flags";
    }
    leaf context {
      xr:xr-xml-map "l2fib:Context";
      type uint16;
      description "Context";
    }
    leaf sequence-resync-threshold {
      xr:xr-xml-map "l2fib:SequenceResyncThreshold";
      type uint16;
      description "Sequence Resync Threshold";
    }
    leaf bound {
      xr:xr-xml-map "l2fib:Bound";
      type boolean;
      description "Bound";
    }
    leaf next-hop-valid {
      xr:xr-xml-map "l2fib:NextHopValid";
      type boolean;
      description "IS Next Hop Valid";
    }
    leaf backup-configured {
      xr:xr-xml-map "l2fib:BackupConfigured";
      type boolean;
      description "Backup Pseudowire Configured";
    }
    leaf redundancy-role {
      xr:xr-xml-map "l2fib:RedundancyRole";
      type L2fib-pw-redundancy-role;
      description "Redundancy Role";
    }
    leaf active {
      xr:xr-xml-map "l2fib:Active";
      type boolean;
      description "PW is active and forwarding";
    }
    leaf pseudo-wire-id-type {
      xr:xr-xml-map "l2fib:PseudoWireIDType";
      type L2fib-pw-id;
      description "Pseudowire ID type";
    }
    leaf pw-load-balance-type {
      xr:xr-xml-map "l2fib:PwLoadBalanceType";
      type L2fib-load-bal;
      description "Type of load-balancing";
    }
    leaf pw-flow-label-tx {
      xr:xr-xml-map "l2fib:PWFlowLabelTX";
      type boolean;
      description "Pseudowire flow label TX enabled";
    }
    leaf grouping-supported {
      xr:xr-xml-map "l2fib:GroupingSupported";
      type boolean;
      description "Grouping supported";
    }
    leaf group-id {
      xr:xr-xml-map "l2fib:GroupID";
      type uint32;
      description "PW Group Id";
    }
    leaf group-state {
      xr:xr-xml-map "l2fib:GroupState";
      type L2fib-group-state;
      description "Group State";
    }
    leaf global-id {
      xr:xr-xml-map "l2fib:GlobalID";
      type uint32;
      description "Global Id";
    }
    leaf ac-id {
      xr:xr-xml-map "l2fib:AcID";
      type uint32;
      description "Ac Id";
    }
    leaf forward-class {
      xr:xr-xml-map "l2fib:ForwardClass";
      type uint8;
      description "Forward Class";
    }
  }

  grouping L2FIB-MONITOR-SESSION-INFO {
    description "L2FIB MONITOR SESSION INFO";

    container base {
      description "Base Information";
      uses L2FIB-BASE-INFO;
    }
    leaf xcid {
      xr:xr-xml-map "l2fib:XCID";
      type uint32;
      description "Xconnect ID";
    }
    leaf session-name {
      xr:xr-xml-map "l2fib:SessionName";
      type string;
      description "Monitor Session Name";
    }
    leaf hardware-information {
      xr:xr-xml-map "l2fib:HardwareInformation";
      type yang:hex-string;
      description "hardware Information of Monitor Session";
    }
    leaf bound {
      xr:xr-xml-map "l2fib:Bound";
      type boolean;
      description "Bound";
    }
  }

  grouping L2FIB-EVPN-INFO {
    description "L2FIB EVPN INFO";

    container base {
      description "Base Information";
      uses L2FIB-BASE-INFO;
    }
    leaf bound {
      xr:xr-xml-map "l2fib:Bound";
      type boolean;
      description "Bound";
    }
    leaf evi {
      xr:xr-xml-map "l2fib:Evi";
      type uint32;
      description "EVPN ID";
    }
    leaf forward-class {
      xr:xr-xml-map "l2fib:ForwardClass";
      type uint8;
      description "Forward Class";
    }
  }

  grouping L2FIB-VNI-INFO {
    description "L2FIB VNI INFO";

    container base {
      description "Base Information";
      uses L2FIB-BASE-INFO;
    }
    leaf srcip {
      xr:xr-xml-map "l2fib:SRCIP";
      type inet:ipv4-address;
      description "VNI Src IPv4 Address";
    }
    leaf mcastip {
      xr:xr-xml-map "l2fib:MCASTIP";
      type inet:ipv4-address;
      description "VNI Mcast IP Address";
    }
    leaf bound {
      xr:xr-xml-map "l2fib:Bound";
      type boolean;
      description "Bound";
    }
    leaf parent-if {
      xr:xr-xml-map "l2fib:ParentIF";
      type xr:Interface-name;
      description "Parent NVE Interface";
    }
    leaf encap {
      xr:xr-xml-map "l2fib:Encap";
      type uint32;
      description "Encap type of VNI";
    }
    leaf udp-port {
      xr:xr-xml-map "l2fib:UDPPort";
      type uint32;
      description "UDP Port";
    }
    leaf source-vtep-if {
      xr:xr-xml-map "l2fib:SourceVtepIF";
      type xr:Interface-name;
      description "Source IF Handle";
    }
    leaf any-cast-ip {
      xr:xr-xml-map "l2fib:AnyCastIP";
      type inet:ipv4-address;
      description "Anycast VTEP IP";
    }
    leaf anycast-mcast-ip {
      xr:xr-xml-map "l2fib:AnycastMcastIP";
      type inet:ipv4-address;
      description "Anycast Multicast IP";
    }
    leaf vx-lan-mode {
      xr:xr-xml-map "l2fib:VxLanMode";
      type uint32;
      description "Vxlan mode";
    }
  }

  grouping L2FIB-PBB-CORE-INFO {
    description "L2FIB PBB CORE INFO";
    leaf vlan-id {
      xr:xr-xml-map "l2fib:vlan_id";
      type uint32;
      description "vlan id";
    }
  }

  grouping L2FIB-PBB-EDGE-INFO {
    description "L2FIB PBB EDGE INFO";
    leaf mac-configured {
      xr:xr-xml-map "l2fib:MacConfigured";
      type boolean;
      description "Configured MAC";
    }
    leaf mac {
      xr:xr-xml-map "l2fib:MAC";
      type yang:mac-address;
      description "unknown unicast bmac";
    }
  }

  grouping L2FIB-PBB-UN {
    description "L2FIB PBB UN";

    container edge {
      when "../pbb-type = 'mgmt-l2fib-bridge-type-pbb-edge'" {
        description
          "../PbbType = 'MGMT_L2FIB_BRIDGE_TYPE_PBB_EDGE'";
      }
      description "edge";
      uses L2FIB-PBB-EDGE-INFO;
    }

    container core {
      when "../pbb-type = 'mgmt-l2fib-bridge-type-pbb-core'" {
        description
          "../PbbType = 'MGMT_L2FIB_BRIDGE_TYPE_PBB_CORE'";
      }
      description "core";
      uses L2FIB-PBB-CORE-INFO;
    }
    leaf pbb-type {
      xr:xr-xml-map "l2fib:PbbType";
      type Mgmt-l2fib-bridge;
      description "PbbType";
    }
  }

  grouping L2FIB-PBB-INFO {
    description "L2FIB PBB INFO";

    container base {
      description "Base Information";
      uses L2FIB-BASE-INFO;
    }

    container pbb-union {
      description "Union of Edge and Core";
      uses L2FIB-PBB-UN;
    }
    leaf bound {
      xr:xr-xml-map "l2fib:Bound";
      type boolean;
      description "Bound";
    }
    leaf forward-class {
      xr:xr-xml-map "l2fib:ForwardClass";
      type uint8;
      description "Forward Class";
    }
    leaf core-pbb-evpn-enabled {
      xr:xr-xml-map "l2fib:CorePBB_EVPNEnabled";
      type boolean;
      description "Core PBB-EVPN enabled";
    }
  }

  grouping L2FIB-AC-INFO {
    description "L2FIB AC INFO";

    container base {
      description "Base Information";
      uses L2FIB-BASE-INFO;
    }
    leaf interface-handle {
      xr:xr-xml-map "l2fib:InterfaceHandle";
      type xr:Interface-name;
      description "Interface Handle";
    }
    leaf sub-interface-handle {
      xr:xr-xml-map "l2fib:SubInterfaceHandle";
      type xr:Interface-name;
      description "Sub Interface Handle";
    }
    leaf attachment-circuit-id {
      xr:xr-xml-map "l2fib:AttachmentCircuitID";
      type uint32;
      description "Attachment Circuit ID";
    }
    leaf attachment-circuit-mtu {
      xr:xr-xml-map "l2fib:AttachmentCircuitMTU";
      type uint16;
      description "MTU of Attachment Circuit";
    }
    leaf actype {
      xr:xr-xml-map "l2fib:ACType";
      type uint8;
      description "Attachment Circuit Type";
    }
    leaf inter-working-mode {
      xr:xr-xml-map "l2fib:InterWorkingMode";
      type uint8;
      description "Interworking Mode";
    }
    leaf adjacency-valid {
      xr:xr-xml-map "l2fib:AdjacencyValid";
      type boolean;
      description "Adjacency Valid";
    }
    leaf adjacency-address {
      xr:xr-xml-map "l2fib:AdjacencyAddress";
      type inet:ipv4-address;
      description "Adjacency Valid";
    }
    leaf bound {
      xr:xr-xml-map "l2fib:Bound";
      type boolean;
      description "Bound";
    }
    leaf ip-inter-working-mac {
      xr:xr-xml-map "l2fib:IPInterWorkingMAC";
      type string;
      description "IP Interworking MAC";
    }
    leaf redundancy-group-id {
      xr:xr-xml-map "l2fib:RedundancyGroupID";
      type uint32;
      description "ICCP Redundancy Group ID";
    }
    leaf redundancy-object-id {
      xr:xr-xml-map "l2fib:RedundancyObjectID";
      type uint64;
      description "ICCP Redundancy Object ID";
    }
  }

  grouping L2FIB-SEG1-UN {
    description "L2FIB SEG1 UN";

    container ac {
      when "../data-type = 'mgmt-l2fib-data-type-ac'" {
        description "../DataType = 'MGMT_L2FIB_DATA_TYPE_AC'";
      }
      description "ac";
      uses L2FIB-AC-INFO;
    }

    container pbb {
      when "../data-type = 'mgmt-l2fib-data-type-pbb'" {
        description "../DataType = 'MGMT_L2FIB_DATA_TYPE_PBB'";
      }
      description "pbb";
      uses L2FIB-PBB-INFO;
    }

    container vni {
      when "../data-type = 'mgmt-l2fib-data-type-vni'" {
        description "../DataType = 'MGMT_L2FIB_DATA_TYPE_VNI'";
      }
      description "vni";
      uses L2FIB-VNI-INFO;
    }

    container evpn {
      when "../data-type = 'mgmt-l2fib-data-type-evpn'" {
        description "../DataType = 'MGMT_L2FIB_DATA_TYPE_EVPN'";
      }
      description "evpn";
      uses L2FIB-EVPN-INFO;
    }

    container monitor-session {
      when "../data-type = 'mgmt-l2fib-data-type-span'" {
        description "../DataType = 'MGMT_L2FIB_DATA_TYPE_SPAN'";
      }
      description "monitor session";
      uses L2FIB-MONITOR-SESSION-INFO;
    }

    container pw {
      when "../data-type != 'mgmt-l2fib-data-type-ac' and"+
        " ../data-type != 'mgmt-l2fib-data-type-pbb' and"+
        " ../data-type != 'mgmt-l2fib-data-type-vni' and"+
        " ../data-type != 'mgmt-l2fib-data-type-evpn' and"+
        " ../data-type != 'mgmt-l2fib-data-type-span'" {
          description
            "../DataType != 'MGMT_L2FIB_DATA_TYPE_AC' and .
            ./DataType != 'MGMT_L2FIB_DATA_TYPE_PBB' and .
            ./DataType != 'MGMT_L2FIB_DATA_TYPE_VNI' and .
            ./DataType != 'MGMT_L2FIB_DATA_TYPE_EVPN' and 
            ../DataType != 'MGMT_L2FIB_DATA_TYPE_SPAN'";
      }
      description "pw";
      uses L2FIB-PW-INFO;
    }
    leaf data-type {
      xr:xr-xml-map "l2fib:DataType";
      type Mgmt-l2fib-data;
      description "DataType";
    }
  }

  grouping L2FIB-BASE-INFO {
    description "L2FIB BASE INFO";
  }

  grouping L2FIB-XCON-INFO {
    description "L2FIB XCON INFO";

    container base {
      description "Base Information";
      uses L2FIB-BASE-INFO;
    }

    container segment1 {
      description "Segment1 Information";
      uses L2FIB-SEG1-UN;
    }

    container segment2 {
      description "Segment2 Information";
      uses L2FIB-SEG2-UN;
    }
    leaf bound {
      xr:xr-xml-map "l2fib:Bound";
      type boolean;
      description "Bound";
    }
    leaf switching-type {
      xr:xr-xml-map "l2fib:SwitchingType";
      type Mgmt-l2fib-switching;
      description "SW Type";
    }
  }
}
