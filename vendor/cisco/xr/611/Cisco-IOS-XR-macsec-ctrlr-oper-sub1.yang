submodule Cisco-IOS-XR-macsec-ctrlr-oper-sub1 {

  belongs-to Cisco-IOS-XR-macsec-ctrlr-oper {
    prefix Cisco-IOS-XR-macsec-ctrlr-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR macsec-ctrlr package operational data.

     Copyright (c) 2013-2016 by Cisco Systems, Inc.
     All rights reserved.";

  revision "2015-11-09" {
    description
      "IOS XR 6.0 revision.";
  }

  typedef Macsec-ctrlr-ciphersuit {
    type enumeration {
      enum gcm-aes-256 {
        value 0;
        description "GCM AES 256";
      }
      enum gcm-aes-128 {
        value 1;
        description "GCM AES 128";
      }
    }
    description "Macsec ctrlr ciphersuit";
  }
  typedef Macsec-ctrlr-state {
    type enumeration {
      enum macsec-ctrlr-state-up {
        value 0;
        description "Up";
      }
      enum macsec-ctrlr-state-down {
        value 1;
        description "Down";
      }
      enum macsec-ctrlr-state-admin-down {
        value 2;
        description "Administratively Down";
      }
    }
    description "Macsec ctrlr state";
  }

  grouping MACSEC-CTRLR-AN-STATUS {
    description "AN status";
    leaf association-number {
      xr:xr-xml-map "macsec_ctrlr_show:AssociationNumber";
      type uint8;
      description "Assocition Number";
    }
    leaf confidentiality-offset {
      xr:xr-xml-map "macsec_ctrlr_show:ConfidentialityOffset";
      type uint32;
      description "Confidentiality offset";
    }
    leaf crypto-algo {
      xr:xr-xml-map "macsec_ctrlr_show:CryptoAlgo";
      type Macsec-ctrlr-ciphersuit;
      description "Crypto Algo";
    }
    leaf programmed-time {
      xr:xr-xml-map "macsec_ctrlr_show:ProgrammedTime";
      type string;
      description "Programmed Time";
    }
  }

  grouping MACSEC-CTRLR-SECURE-CHANNEL-STATUS {
    description "Secure Channel status";
    leaf secure-channel-id {
      xr:xr-xml-map "macsec_ctrlr_show:SecureChannelId";
      type uint64;
      description "Secure Channel Id";
    }
    leaf xpn-enabled {
      xr:xr-xml-map "macsec_ctrlr_show:XpnEnabled";
      type boolean;
      description "XPN Enabled";
    }

    list active-association {
      description "Active Associations";
      uses MACSEC-CTRLR-AN-STATUS;
    }
  }

  grouping MACSEC-CTRLR-IF-STATUS {
    description "Interface Status details";

    container encrypt-secure-channel-status {
      description "Encrypt Secure Channel Status";
      uses MACSEC-CTRLR-SECURE-CHANNEL-STATUS;
    }

    container decrypt-secure-channel-status {
      description "Decrypt Secure Channel Status";
      uses MACSEC-CTRLR-SECURE-CHANNEL-STATUS;
    }
    leaf state {
      xr:xr-xml-map "macsec_ctrlr_show:State";
      type Macsec-ctrlr-state;
      description "State";
    }
    leaf replay-window-size {
      xr:xr-xml-map "macsec_ctrlr_show:ReplayWindowSize";
      type uint32;
      description "Replay Window Size";
    }
    leaf must-secure {
      xr:xr-xml-map "macsec_ctrlr_show:MustSecure";
      type boolean;
      description "Must Secure";
    }
    leaf sec-tag-offset {
      xr:xr-xml-map "macsec_ctrlr_show:SecTagOffset";
      type uint32;
      description "Sec Tag Offset";
    }
  }
}
