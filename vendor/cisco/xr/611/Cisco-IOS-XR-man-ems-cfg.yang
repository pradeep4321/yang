module Cisco-IOS-XR-man-ems-cfg {

  /*** NAMESPACE / PREFIX DEFINITION ***/

  namespace "http://cisco.com/ns/yang/Cisco-IOS-XR-man-ems-cfg";


  prefix "man-ems-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR man-ems package configuration.

     This module contains definitions
     for the following management objects:
       grpc: GRPC configruation

     Copyright (c) 2013-2016 by Cisco Systems, Inc.
     All rights reserved.";

  revision "2015-11-09" {
    description
      "IOS XR 6.0 revision.";
  }


  container grpc {
    xr:xr-xml-map "cfg_ems:Grpc";
    description "GRPC configruation";

    container tls {
      xr:xr-xml-map "cfg_ems:TLS";
      description "Transport Layer Security (TLS)";
      leaf trustpoint {
        xr:xr-xml-map "cfg_ems:TRUSTPOINT";
        xr:xr-cli-map "trustpoint <string> ";
        type string;
        description "Trustpoint Name";
      }
      leaf enable {
        xr:xr-xml-map "cfg_ems:Enable";
        type empty;
        description "Enable TLS";
      }
    }
    leaf port {
      xr:xr-xml-map "cfg_ems:Port";
      xr:xr-cli-map "grpc port <number> ";
      type uint32 {
        range "57344..57999";
      }
      description "Server listening port";
    }
    leaf enable {
      xr:xr-xml-map "cfg_ems:Enable";
      type empty;
      description "Enable GRPC";
    }
    leaf max-request-per-user {
      xr:xr-xml-map "cfg_ems:MaxRequestPerUser";
      xr:xr-cli-map "grpc max-request-per-user <number> ";
      type uint32 {
        range "1..32";
      }
      description "Maximum concurrent requests per user";
    }
    leaf address-family {
      xr:xr-xml-map "cfg_ems:AddressFamily";
      xr:xr-cli-map "grpc address-family (ipv4)|(ipv6) ";
      type string;
      description "Address family identifier type";
    }
    leaf max-request-total {
      xr:xr-xml-map "cfg_ems:MaxRequestTotal";
      xr:xr-cli-map "grpc max-request-total <number> ";
      type uint32 {
        range "1..256";
      }
      description "Maximum concurrent requests in total";
    }
  }
}
