module Cisco-IOS-XR-man-restconf-cfg {

  /*** NAMESPACE / PREFIX DEFINITION ***/

  namespace "http://cisco.com/ns/yang/Cisco-IOS-XR-man-restconf-cfg";


  prefix "man-restconf-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR man-restconf package configuration.

     This module contains definitions
     for the following management objects:
       restconf: RESTCONF configuration commands

     Copyright (c) 2013-2016 by Cisco Systems, Inc.
     All rights reserved.";

  revision "2015-11-09" {
    description
      "IOS XR 6.0 revision.";
  }


  container restconf {
    xr:xr-xml-map "cfg_restconf:RESTCONF";
    description "RESTCONF configuration commands";

    container agent {
      xr:xr-xml-map "cfg_restconf:Agent";
      description "RESTCONF agent configuration commands";
      leaf open-request-limit {
        xr:xr-xml-map "cfg_restconf:OpenRequestLimit";
        xr:xr-cli-map "restconf [agent] open-request-limit <number>"+
          " ";
        type uint32 {
          range "1..128";
        }
        description
          "Count of allowable concurrent restconf requests";
      }
      leaf enable {
        xr:xr-xml-map "cfg_restconf:Enable";
        type empty;
        description "Enable RESTCONF agent";
      }
      leaf per-user-request-limit {
        xr:xr-xml-map "cfg_restconf:PerUserRequestLimit";
        xr:xr-cli-map "restconf [agent] per-user-request-limit <num"+
          "ber> ";
        type uint32 {
          range "1..32";
        }
        description
          "Count of allowable concurrent restconf requests
          per user";
      }
    }
  }
}
