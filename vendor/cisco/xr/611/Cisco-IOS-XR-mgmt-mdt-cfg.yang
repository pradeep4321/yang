module Cisco-IOS-XR-mgmt-mdt-cfg {

  /*** NAMESPACE / PREFIX DEFINITION ***/

  namespace "http://cisco.com/ns/yang/Cisco-IOS-XR-mgmt-mdt-cfg";


  prefix "mgmt-mdt-cfg";

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR mgmt-mdt package configuration.

     This module contains definitions
     for the following management objects:
       m2m: M2M configruation

     Copyright (c) 2013-2016 by Cisco Systems, Inc.
     All rights reserved.";

  revision "2015-11-09" {
    description
      "IOS XR 6.0 revision.";
  }

  typedef Proto-type {
    type enumeration {
      enum grpc {
        value 1;
        description "GRPC";
      }
      enum tcp {
        value 2;
        description "tcp";
      }
      enum udp {
        value 3;
        description "udp";
      }
      enum netconf {
        value 4;
        description "netconf";
      }
      enum restconf {
        value 5;
        description "restconf";
      }
    }
    description "Proto type";
  }
  typedef Encode-type {
    type enumeration {
      enum gpb {
        value 2;
        description "GPB";
      }
      enum self-describing-gpb {
        value 3;
        description "SELF DESCRIBING GPB";
      }
      enum json {
        value 4;
        description "JSON";
      }
      enum xr-xml {
        value 5;
        description "XML";
      }
    }
    description "Encode type";
  }
  typedef Af {
    type enumeration {
      enum ipv4 {
        value 1;
        description "IPv4 address family";
      }
      enum ipv6 {
        value 2;
        description "IPv6 address family";
      }
    }
    description "Af";
  }

  container m2m {
    xr:xr-xml-map "cfg_mdt:m2m";
    description "M2M configruation";

    container mdt {
      xr:xr-xml-map "cfg_mdt:mdt";
      description "Model Driver Telemetry configuration";

      container sensor-groups {
        xr:xr-xml-map "cfg_mdt:SensorGroupTable";
        description "Sensor group configuration";

        list sensor-group {
          xr:xr-xml-map "cfg_mdt:SensorGroup";
          key "sensor-group-identifier";
          description "Sensor group configuration";

          container sensor-paths {
            xr:xr-xml-map "cfg_mdt:SensorPathTable";
            description "Sensor path configuration";

            list sensor-path {
              xr:xr-xml-map "cfg_mdt:SensorPath";
              key "telemetry-sensor-path";
              description "Sensor path configuration";
              leaf telemetry-sensor-path {
                xr:xr-xml-map "cfg_mdt:TelemetrySensorPath";
                type xr:Cisco-ios-xr-string;
                description "Sensor Path";
              }
            }
          }
          leaf enable {
            xr:xr-xml-map "cfg_mdt:Enable";
            type empty;
            description "Enable Sensor Group";
          }
          leaf sensor-group-identifier {
            xr:xr-xml-map "cfg_mdt:SensorGroupIdentifier";
            type xr:Cisco-ios-xr-string;
            description "The identifier for this group";
          }
        }
      }

      container subscriptions {
        xr:xr-xml-map "cfg_mdt:SubscriptionTable";
        description "Streaming Telemetry Subscription";

        list subscription {
          xr:xr-xml-map "cfg_mdt:Subscription";
          key "subscription-identifier";
          description "Streaming Telemetry Subscription";

          container source-address {
            xr:xr-xml-map "cfg_mdt:source-address";
            presence "Indicates a source-address node is"+
              " configured.";
            description
              "Source address to use for streaming telemetry
              information";
            leaf aftype {
              xr:xr-xml-map "cfg_mdt:aftype";
              type Af;
              mandatory true;
              description "Address Family type, IPv4|IPv6";
            }
            leaf ip-address {
              xr:xr-xml-map "cfg_mdt:IPAddress";
              type inet:ipv4-address-no-zone;
              description "Source IPv4 address";
            }
            leaf ipv6-address {
              xr:xr-xml-map "cfg_mdt:IPv6Address";
              type string;
              description "IPV6 address of the Source";
            }
          }

          container sensor-profiles {
            xr:xr-xml-map "cfg_mdt:SensorProfileTable";
            description "Associate Sensor Groups with Subscription";

            list sensor-profile {
              xr:xr-xml-map "cfg_mdt:SensorProfile";
              key "sensorgroupid";
              description
                "Associate Sensor Group with Subscription";
              leaf sample-interval {
                xr:xr-xml-map "cfg_mdt:sample-interval";
                xr:xr-cli-map "mdt subscription <string> sensor-gro"+
                  "up-id <string> sample-interval <number> ";
                type uint32 {
                  range "500..3600000";
                }
                units "millisecond";
                description "Sample interval in milliseconds";
              }
              leaf heartbeat-interval {
                xr:xr-xml-map "cfg_mdt:heartbeat-interval";
                xr:xr-cli-map "mdt subscription <string> sensor-gro"+
                  "up-id <string> heartbeat-interval <number> ";
                type uint32 {
                  range "0..4294967295";
                }
                units "second";
                description "Heartbeat interval in Seconds";
              }
              leaf supress-redundant {
                xr:xr-xml-map "cfg_mdt:supress-redundant";
                xr:xr-cli-map "mdt subscription <string> sensor-gro"+
                  "up-id <string> suppress-redundant ";
                type empty;
                description "Supress Redundant updates";
              }
              leaf sensorgroupid {
                xr:xr-xml-map "cfg_mdt:sensorgroupid";
                type xr:Cisco-ios-xr-string;
                description
                  "Reference to the telemetry sensor group
                  name";
              }
            }
          }

          container destination-profiles {
            xr:xr-xml-map "cfg_mdt:DestinationProfileTable";
            description
              "Associate Destination Groups with
              Subscription";

            list destination-profile {
              xr:xr-xml-map "cfg_mdt:DestinationProfile";
              key "destination-id";
              description
                "Associate Destination Group with
                Subscription";
              leaf enable {
                xr:xr-xml-map "cfg_mdt:Enable";
                xr:xr-cli-map "mdt subscription <string> destinatio"+
                  "n-id <string> ";
                type empty;
                description
                  "Associate destintion id with Subscription";
              }
              leaf destination-id {
                xr:xr-xml-map "cfg_mdt:DestinationId";
                type xr:Cisco-ios-xr-string;
                description
                  "Destination Id to associate with
                  Subscription";
              }
            }
          }
          leaf source-qos-marking {
            xr:xr-xml-map "cfg_mdt:source-qos-marking";
            xr:xr-cli-map "mdt subscription <string> source-qos-mar"+
              "king <number> ";
            type uint32 {
              range "10..300";
            }
            description "Outgoing DSCP value";
          }
          leaf subscription-identifier {
            xr:xr-xml-map "cfg_mdt:SubscriptionIdentifier";
            type xr:Cisco-ios-xr-string;
            description "Subscription identifier string";
          }
        }
      }

      container destination-groups {
        xr:xr-xml-map "cfg_mdt:DestinationGroupTable";
        description "Destination Group configuration";

        list destination-group {
          xr:xr-xml-map "cfg_mdt:DestinationGroup";
          key "destination-id";
          description "Destination Group";

          container destinations {
            xr:xr-xml-map "cfg_mdt:DestinationTable";
            description "Destination configuration";

            list destination {
              xr:xr-xml-map "cfg_mdt:Destination";
              must "ipv4 or ipv6" {
                description "IPv4 or IPv6 must be present.";
              }
              key "address-family";
              description "Destination address configuration";

              grouping DESTINATION-CONTENT {
                description "DESTINATION CONTENT";
                leaf encoding {
                  type Encode-type;
                  description
                    "Encoding used to transmit telemetry data
                    to the collector";
                }
                leaf protocol {
                  xr:xr-xml-map "cfg_mdt:protocol";
                  type Proto-type;
                  description
                    "Transport Protocol used to transmit
                    telemetry data to the collector";
                }
              }
              leaf address-family {
                xr:xr-xml-map "cfg_mdt:address-family";
                type Af;
                description "Address Family type, IPv4|IPv6";
              }

              list ipv4 {
                xr:xr-xml-map "cfg_mdt:encoding";
                when "../address-family = 'ipv4'" {
                  description "../address-family = IPv4";
                }
                key "ipv4-address destination-port";
                description "ipv4";
                leaf ipv4-address {
                  xr:xr-xml-map "cfg_mdt:IPv4Address";
                  type inet:ip-address-no-zone;
                  description "Destination IPv4 address";
                }
                leaf destination-port {
                  xr:xr-xml-map "cfg_mdt:destination-port";
                  type inet:port-number;
                  description "destination port";
                }
                uses DESTINATION-CONTENT;
              }

              list ipv6 {
                xr:xr-xml-map "cfg_mdt:encoding";
                when "../address-family = 'ipv6'" {
                  description "../address-family = IPv6";
                }
                key "ipv6-address destination-port";
                description "ipv6";
                leaf ipv6-address {
                  xr:xr-xml-map "cfg_mdt:IPv6Address";
                  type xr:Cisco-ios-xr-string;
                  description "IPV6 address of the destination";
                }
                leaf destination-port {
                  xr:xr-xml-map "cfg_mdt:destination-port";
                  type inet:port-number;
                  description "destination port";
                }
                uses DESTINATION-CONTENT;
              }
            }
          }
          leaf destination-id {
            xr:xr-xml-map "cfg_mdt:DestinationId";
            type xr:Cisco-ios-xr-string;
            description "destination group id string";
          }
        }
      }
      leaf enable {
        xr:xr-xml-map "cfg_mdt:Enable";
        type empty;
        description "Enable MDT";
      }
    }
  }
}
