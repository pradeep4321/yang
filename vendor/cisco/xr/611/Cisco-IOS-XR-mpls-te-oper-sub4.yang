submodule Cisco-IOS-XR-mpls-te-oper-sub4 {

  belongs-to Cisco-IOS-XR-mpls-te-oper {
    prefix Cisco-IOS-XR-mpls-te-oper;
  }

  /*** LINKAGE (IMPORTS / INCLUDES) ***/

  import ietf-inet-types { prefix "inet"; }

  import Cisco-IOS-XR-types { prefix "xr"; }

  include Cisco-IOS-XR-mpls-te-oper-sub6 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR mpls-te package operational data.

     Copyright (c) 2013-2016 by Cisco Systems, Inc.
     All rights reserved.";

  revision "2015-11-09" {
    description
      "IOS XR 6.0 revision.";
  }

  typedef Pce-tunnel-state {
    type enumeration {
      enum tunnel-state-none {
        description "None";
      }
      enum tunnel-state-admin-down {
        description "AdminDown";
      }
      enum tunnel-state-down {
        description "Down";
      }
      enum tunnel-state-up {
        description "Up";
      }
    }
    description "PCE Tunnel State";
  }
  typedef Pce-tun-path-state {
    type enumeration {
      enum state-none {
        description "None";
      }
      enum state-pending {
        description "Request Pending";
      }
      enum state-received-path {
        description "Path Received";
      }
      enum state-no-peer {
        description "No peer to forward";
      }
      enum state-pcep-down {
        description "PCEP to the peer is down";
      }
      enum state-received-no-path {
        description "Path Received No Path";
      }
    }
    description "PCE Request State";
  }
  typedef Pce-state {
    type enumeration {
      enum tcp-close {
        description "TCP close";
      }
      enum tcp-listen {
        description "TCP listen";
      }
      enum tcp-connect {
        description "TCP connect";
      }
      enum pcep-closed {
        description "PCEP closed";
      }
      enum pcep-opening {
        description "PCEP opening";
      }
      enum pcep-open {
        description "PCEP open";
      }
    }
    description "PCE State";
  }
  typedef Pce-lsp-autoroute-metric {
    type enumeration {
      enum none {
        description "None";
      }
      enum relative {
        description "Relative";
      }
      enum absolute {
        description "Absolute";
      }
    }
    description "Autoroute Metric Type";
  }
  typedef Pce-sr-sid {
    type enumeration {
      enum unknown-segment-id {
        description "Unknown type";
      }
      enum ipv4-node-segment-id {
        description "IPv4 Node ID";
      }
      enum ipv4-adjacency-segment-id {
        description "IPv4 Adjacency ID";
      }
    }
    description "PCE SID type";
  }
  typedef Pce-lsp-oper-state {
    type enumeration {
      enum down {
        description "Down";
      }
      enum up {
        description "Up";
      }
      enum active {
        description "Active";
      }
      enum going-down {
        description "Going down";
      }
      enum going-up {
        description "Going Up";
      }
    }
    description "LSP Operational state";
  }

  grouping PCE-TUNNEL-BAG {
    description "PCE Tunnel Summary Information";
    leaf error {
      xr:xr-xml-map "te_pce:Error";
      type string;
      description "Error (for display only)";
    }
    leaf tunnel-name-xr {
      xr:xr-xml-map "te_pce:tunnel-name-xr";
      type string;
      description "Tunnel Name";
    }
    leaf source-address {
      xr:xr-xml-map "te_pce:SourceAddress";
      type inet:ipv4-address;
      description "Source Address";
    }
    leaf destination-address {
      xr:xr-xml-map "te_pce:DestinationAddress";
      type inet:ipv4-address;
      description "Destination Address";
    }
    leaf is-curr-path-option-pce {
      xr:xr-xml-map "te_pce:IsCurrPathOptionPCE";
      type boolean;
      description "True if current path option is PCE based";
    }
    leaf curr-path-option-index {
      xr:xr-xml-map "te_pce:CurrPathOptionIndex";
      type uint32;
      description "Path Option Index of the current path";
    }
    leaf configured-pce-address {
      xr:xr-xml-map "te_pce:ConfiguredPCEAddress";
      type inet:ipv4-address;
      description "Configured PCE Address";
    }
    leaf sender-pce-address {
      xr:xr-xml-map "te_pce:SenderPCEAddress";
      type inet:ipv4-address;
      description "Sender PCE Address";
    }
    leaf path-state {
      xr:xr-xml-map "te_pce:PathState";
      type Pce-tun-path-state;
      description "Path Request State";
    }
    leaf tunnel-state {
      xr:xr-xml-map "te_pce:TunnelState";
      type Pce-tunnel-state;
      description "Tunnel State";
    }
    leaf admin-weight {
      xr:xr-xml-map "te_pce:AdminWeight";
      type uint32;
      description "Path metric";
    }
    leaf hop-count {
      xr:xr-xml-map "te_pce:HopCount";
      type uint32;
      description "Hop Count";
    }
  }

  grouping PCE-NODE-BAG {
    description "PCE Node Information";
    leaf router-id {
      xr:xr-xml-map "te_pce:RouterID";
      type inet:ipv4-address;
      description "Router ID";
    }
    leaf igp-area-id {
      xr:xr-xml-map "te_pce:IGPAreaID";
      type uint32;
      description "IGP Area number";
    }
    leaf igp-area-format {
      xr:xr-xml-map "te_pce:IGPAreaFormat";
      type Igp-ospf-area-format;
      description "IGP Area Format";
    }
    leaf pce-cost {
      xr:xr-xml-map "te_pce:PCECost";
      type uint32;
      description "PCE cost";
    }
    leaf node-id {
      xr:xr-xml-map "te_pce:NodeID";
      type inet:ipv4-address;
      description "Node ID";
    }
    leaf is-pce-border-node {
      xr:xr-xml-map "te_pce:IsPCEBorderNode";
      type boolean;
      description "PCE border node";
    }
  }

  grouping PCE-TOPOLOGY-GLOBAL-INFO-BAG {
    description "PCE Topology Information";

    list nodes {
      description "Node information";
      uses PCE-NODE-BAG;
    }
  }

  grouping PCEERR-BAG {
    description "PCE Error information";
    leaf pce-err-type {
      xr:xr-xml-map "te_pce:PCEErrType";
      type uint32;
      description "PCE Error Type";
    }
    leaf pce-err-value {
      xr:xr-xml-map "te_pce:PCEErrValue";
      type uint32;
      description "PCE Error Value";
    }
    leaf has-open-object {
      xr:xr-xml-map "te_pce:HasOpenObject";
      type boolean;
      description "Has Open object";
    }
    leaf openversion {
      xr:xr-xml-map "te_pce:OpenVersion";
      type uint32;
      description "Open Version";
    }
    leaf open-keepalive {
      xr:xr-xml-map "te_pce:OpenKeepalive";
      type uint32;
      units "second";
      description "Open Keepalive (seconds)";
    }
    leaf open-dead-time {
      xr:xr-xml-map "te_pce:OpenDeadTime";
      type uint32;
      units "second";
      description "Open Deadtime (seconds)";
    }
    leaf has-rp-object {
      xr:xr-xml-map "te_pce:HasRPObject";
      type boolean;
      description "Has RP object";
    }
    leaf rp-request-id {
      xr:xr-xml-map "te_pce:RPRequestID";
      type uint32;
      description "RP request ID";
    }
  }

  grouping PCE-PEER-IGP-BAG {
    description "PCE IGP information";
    leaf igp-type {
      xr:xr-xml-map "te_pce:IGPType";
      type Igp-protocol;
      description "Type";
    }
    leaf igp-instance-id {
      xr:xr-xml-map "te_pce:IGPInstanceID";
      type string;
      description "Instance ID";
    }
  }

  grouping PCE-NEIGHBOR-BAG {
    description "PCE Neighbor Information";

    container last-tx-pce-err {
      description "Last sent PCEErr";
      uses PCEERR-BAG;
    }

    container last-rx-pce-err {
      description "Last received PCEErr";
      uses PCEERR-BAG;
    }
    leaf error {
      xr:xr-xml-map "te_pce:Error";
      type string;
      description "Error (for display only)";
    }
    leaf speaker-id {
      xr:xr-xml-map "te_pce:SpeakerID";
      type string;
      description "Speaker Entity ID";
    }
    leaf pce-address {
      xr:xr-xml-map "te_pce:PCEAddress";
      type inet:ipv4-address;
      description "PCE Address";
    }
    leaf pce-state {
      xr:xr-xml-map "te_pce:PCEState";
      type Pce-state;
      description "PCE State";
    }
    leaf precedence {
      xr:xr-xml-map "te_pce:Precedence";
      type uint32;
      description "PCE Precedence";
    }
    leaf stateful {
      xr:xr-xml-map "te_pce:Stateful";
      type boolean;
      description "Stateful";
    }
    leaf capability-update {
      xr:xr-xml-map "te_pce:CapabilityUpdate";
      type boolean;
      description "Update capability";
    }
    leaf capability-instantiate {
      xr:xr-xml-map "te_pce:CapabilityInstantiate";
      type boolean;
      description "Instantiation capability";
    }
    leaf capability-segment-routing {
      xr:xr-xml-map "te_pce:CapabilitySegmentRouting";
      type boolean;
      description "Segment Routing capability";
    }
    leaf triggered-sync-capability {
      xr:xr-xml-map "te_pce:TriggeredSyncCapability";
      type boolean;
      description "Triggered Synchronization capability";
    }
    leaf capability-db-version {
      xr:xr-xml-map "te_pce:CapabilityDBVersion";
      type boolean;
      description "DB version capability";
    }
    leaf delta-sync-capability {
      xr:xr-xml-map "te_pce:DeltaSyncCapability";
      type boolean;
      description "Delta Synchronization capability";
    }
    leaf pcep-up-time {
      xr:xr-xml-map "te_pce:PCEPUpTime";
      type uint32;
      description "PCEP Up Time";
    }
    leaf keepalives {
      xr:xr-xml-map "te_pce:Keepalives";
      type uint32;
      description "Keepalive count";
    }
    leaf candidate {
      xr:xr-xml-map "te_pce:Candidate";
      type boolean;
      description "Candidate";
    }
    leaf statically-configured {
      xr:xr-xml-map "te_pce:StaticallyConfigured";
      type boolean;
      description "Statically Configured";
    }
    leaf md5-enabled {
      xr:xr-xml-map "te_pce:MD5Enabled";
      type boolean;
      description "MD5 Authentication Enabled";
    }
    leaf keychain-enabled {
      xr:xr-xml-map "te_pce:KeychainEnabled";
      type boolean;
      description "Keychain based Authentication Enabled";
    }
    leaf negotiated-keepalive {
      xr:xr-xml-map "te_pce:NegotiatedKeepalive";
      type uint32;
      description "Negotiated KA";
    }
    leaf negotated-dead-time {
      xr:xr-xml-map "te_pce:NegotatedDeadTime";
      type uint32;
      description "Negotiated DT";
    }
    leaf pce-req-rx {
      xr:xr-xml-map "te_pce:PCEReqRx";
      type uint32;
      description "PCEReq Rx";
    }
    leaf pce-req-tx {
      xr:xr-xml-map "te_pce:PCEReqTx";
      type uint32;
      description "PCEReq Tx";
    }
    leaf pce-rep-rx {
      xr:xr-xml-map "te_pce:PCERepRx";
      type uint32;
      description "PCERep Rx";
    }
    leaf pce-rep-tx {
      xr:xr-xml-map "te_pce:PCERepTx";
      type uint32;
      description "PCERep Tx";
    }
    leaf pce-err-rx {
      xr:xr-xml-map "te_pce:PCEErrRx";
      type uint32;
      description "PCEErr Rx";
    }
    leaf pce-err-tx {
      xr:xr-xml-map "te_pce:PCEErrTx";
      type uint32;
      description "PCEErr Tx";
    }
    leaf pce-open-tx {
      xr:xr-xml-map "te_pce:PCEOpenTx";
      type uint32;
      description "PCEOpen Tx";
    }
    leaf pce-open-rx {
      xr:xr-xml-map "te_pce:PCEOpenRx";
      type uint32;
      description "PCEOpen Rx";
    }
    leaf pce-rpt-rx {
      xr:xr-xml-map "te_pce:PCERptRx";
      type uint32;
      description "PCERpt Rx";
    }
    leaf pce-rpt-tx {
      xr:xr-xml-map "te_pce:PCERptTx";
      type uint32;
      description "PCERpt Tx";
    }
    leaf pce-upd-rx {
      xr:xr-xml-map "te_pce:PCEUpdRx";
      type uint32;
      description "PCEUpd Rx";
    }
    leaf pce-upd-tx {
      xr:xr-xml-map "te_pce:PCEUpdTx";
      type uint32;
      description "PCEUpd Tx";
    }
    leaf pce-init-rx {
      xr:xr-xml-map "te_pce:PCEInitRx";
      type uint32;
      description "PCEInit Rx";
    }
    leaf pce-init-tx {
      xr:xr-xml-map "te_pce:PCEInitTx";
      type uint32;
      description "PCEInit Tx";
    }
    leaf pce-keepalive-tx {
      xr:xr-xml-map "te_pce:PCEKeepaliveTx";
      type uint64;
      description "PCE Keepalive Tx";
    }
    leaf pce-keepalive-rx {
      xr:xr-xml-map "te_pce:PCEKeepaliveRx";
      type uint64;
      description "PCE Keepalive Rx";
    }
    leaf req-reply-min {
      xr:xr-xml-map "te_pce:ReqReplyMin";
      type uint64;
      description "Mininum reply time from peer in ms";
    }
    leaf req-reply-max {
      xr:xr-xml-map "te_pce:ReqReplyMax";
      type uint64;
      description "Maximum reply time from peer in ms";
    }
    leaf req-reply-avg {
      xr:xr-xml-map "te_pce:ReqReplyAvg";
      type uint64;
      description "Average reply time from peer in ms";
    }
    leaf request-timeouts {
      xr:xr-xml-map "te_pce:RequestTimeouts";
      type uint64;
      description "Request timeout count";
    }
    leaf local-sid {
      xr:xr-xml-map "te_pce:LocalSID";
      type uint8;
      description "Local PCEP session ID";
    }
    leaf remote-sid {
      xr:xr-xml-map "te_pce:RemoteSID";
      type uint8;
      description "Remote PCEP session ID";
    }
    leaf min-keepalive-interval {
      xr:xr-xml-map "te_pce:MinKeepaliveInterval";
      type uint8;
      description "Minimum keepalive interval for the peer";
    }
    leaf max-dead-interval {
      xr:xr-xml-map "te_pce:MaxDeadInterval";
      type uint8;
      description "Maximum dead interval for the peer";
    }

    list ig-ps {
      description "IGPs";
      uses PCE-PEER-IGP-BAG;
    }
  }

  grouping PCE-IGP-STATS-BAG {
    description "PCE IGP Stats";
    leaf abr-lookup-min {
      xr:xr-xml-map "te_pce:ABRLookupMin";
      type uint64;
      description "ABR Lookup Min";
    }
    leaf abr-lookup-max {
      xr:xr-xml-map "te_pce:ABRLookupMax";
      type uint64;
      description "ABR Lookup Max";
    }
    leaf abr-lookup-avg {
      xr:xr-xml-map "te_pce:ABRLookupAvg";
      type uint64;
      description "ABR Lookup Avg";
    }
    leaf abr-lookup-timeout {
      xr:xr-xml-map "te_pce:ABRLookupTimeout";
      type uint64;
      description "ABR Lookup Timeout";
    }
    leaf abr-lookup-complete {
      xr:xr-xml-map "te_pce:ABRLookupComplete";
      type uint64;
      description "ABR Lookup Complete";
    }
  }

  grouping PCE-STATS-BAG {
    description "PCE Stats Information";

    container igp-statistics {
      description "IGP Statistics";
      uses PCE-IGP-STATS-BAG;
    }
    leaf neighbors {
      xr:xr-xml-map "te_pce:Neighbors";
      type uint32;
      description "Neighbor Count";
    }
    leaf tunnels {
      xr:xr-xml-map "te_pce:Tunnels";
      type uint32;
      description "Tunnel Count";
    }
    leaf pce-req-total {
      xr:xr-xml-map "te_pce:PCEReqTotal";
      type uint32;
      description "Total number of PCEReq";
    }
    leaf pce-req-pending {
      xr:xr-xml-map "te_pce:PCEReqPending";
      type uint32;
      description "Number of pending req";
    }
    leaf pce-req-timed-out {
      xr:xr-xml-map "te_pce:PCEReqTimedOut";
      type uint32;
      description "Number of timedout req";
    }
    leaf max-file-descriptors {
      xr:xr-xml-map "te_pce:MaxFileDescriptors";
      type uint32;
      description "Maximum number of TCP file descriptors used";
    }
    leaf current-file-descriptors {
      xr:xr-xml-map "te_pce:CurrentFileDescriptors";
      type uint32;
      description "Number of TCP file descriptors currently in use";
    }
    leaf current-pceq-length {
      xr:xr-xml-map "te_pce:CurrentPCEQLength";
      type uint32;
      description "Current PCE queue length";
    }
    leaf current-teq-length {
      xr:xr-xml-map "te_pce:CurrentTEQLength";
      type uint32;
      description "Current TE queue length";
    }
    leaf max-pceq-length {
      xr:xr-xml-map "te_pce:MaxPCEQLength";
      type uint32;
      description "Max PCE queue length";
    }
    leaf max-teq-length {
      xr:xr-xml-map "te_pce:MaxTEQLength";
      type uint32;
      description "Max TE queue length";
    }
    leaf-list maximum-in-queue-depth {
      xr:xr-xml-map "te_pce:MaximumInQueueDepth";
      type uint32;
      max-elements "3";
      description "Max Input Queue Depth";
    }
    leaf-list average-in-queue-depth {
      xr:xr-xml-map "te_pce:AverageInQueueDepth";
      type uint32;
      max-elements "3";
      description "Average Input Queue Depth";
    }
  }

  grouping PCE-LSP-AUTOROUTE-BAG {
    description "LSP Autoroute Information";
    leaf is-used {
      xr:xr-xml-map "te_pce:IsUsed";
      type boolean;
      description "Autoroute used flag";
    }
    leaf announced {
      xr:xr-xml-map "te_pce:Announced";
      type boolean;
      description "Autoroute announced";
    }
    leaf metric-type {
      xr:xr-xml-map "te_pce:MetricType";
      type Pce-lsp-autoroute-metric;
      description "Metric Type";
    }
    leaf metric {
      xr:xr-xml-map "te_pce:Metric";
      type uint32;
      description "Metric Value";
    }
    leaf-list destination {
      xr:xr-xml-map "te_pce:Destinations";
      type inet:ipv4-address;
      description "Destinations";
    }
  }

  grouping PCE-LSP-METRIC-BAG {
    description "PCE LSP Metric Object";
    leaf type {
      xr:xr-xml-map "te_pce:Type";
      type uint8;
      description "Type";
    }
    leaf cost {
      xr:xr-xml-map "te_pce:Cost";
      type uint32;
      description "Cost";
    }
  }

  grouping PCE-LSP-LSPA-BAG {
    description "PCE LSP Attributes Object";
    leaf is-used {
      xr:xr-xml-map "te_pce:IsUsed";
      type boolean;
      description "LSPA used flag";
    }
    leaf exlude-any {
      xr:xr-xml-map "te_pce:ExludeAny";
      type uint32;
      description "Exclude Any";
    }
    leaf include-any {
      xr:xr-xml-map "te_pce:IncludeAny";
      type uint32;
      description "Include Any";
    }
    leaf include-all {
      xr:xr-xml-map "te_pce:IncludeAll";
      type uint32;
      description "Include All";
    }
    leaf setup {
      xr:xr-xml-map "te_pce:Setup";
      type uint8;
      description "Setup";
    }
    leaf hold {
      xr:xr-xml-map "te_pce:Hold";
      type uint8;
      description "Hold";
    }
    leaf lbit {
      xr:xr-xml-map "te_pce:LBit";
      type boolean;
      description "L flag";
    }
  }

  grouping PCE-LSP-ROUTE-HOP-BAG {
    description "PCE LSP Route Subobject";
    leaf subobj-type {
      xr:xr-xml-map "te_pce:SubobjType";
      type uint8;
      description "Route Subobject Type";
    }
    leaf ipv4-address {
      xr:xr-xml-map "te_pce:IPv4Address";
      type inet:ipv4-address;
      description "IPv4 address";
    }
    leaf ipv4-prefix-len {
      xr:xr-xml-map "te_pce:IPv4PrefixLen";
      type uint32;
      description "IPv4 Address Prefix Length";
    }
    leaf strict {
      xr:xr-xml-map "te_pce:Strict";
      type boolean;
      description "Strict";
    }
    leaf global {
      xr:xr-xml-map "te_pce:Global";
      type boolean;
      description "Global";
    }
    leaf mpls-label {
      xr:xr-xml-map "te_pce:MPLSLabel";
      type uint32;
      description "MPLS Label in case Segment ID type is MPLS";
    }
    leaf segment-id-type {
      xr:xr-xml-map "te_pce:SegmentIDType";
      type Pce-sr-sid;
      description "Segment ID Type";
    }
    leaf only-valid-mpls-label {
      xr:xr-xml-map "te_pce:OnlyValidMPLSLabel";
      type boolean;
      description
        "If this flag is true, SID has only MPLS label
        value. TC, S, and TTL fields are considered
        invalid";
    }
    leaf complete-mpls-label-entry {
      xr:xr-xml-map "te_pce:CompleteMPLSLabelEntry";
      type boolean;
      description
        "If this flag is true, all fields of MPLS labe
        entry are valid";
    }
    leaf missing-segment-id {
      xr:xr-xml-map "te_pce:MissingSegmentID";
      type boolean;
      description
        "If this flag is true, ERO subobject does not
        have SegmentID";
    }
    leaf missing-node-adjcency-id {
      xr:xr-xml-map "te_pce:MissingNodeAdjcencyID";
      type boolean;
      description
        "If this flag is true, ERO subobject does not
        have NodeAdjacencyID";
    }
    leaf segment-id-exists {
      xr:xr-xml-map "te_pce:SegmentIDExists";
      type boolean;
      description
        "If this field is true, the bag contains
        SegmentID value";
    }
    leaf segment-id-value {
      xr:xr-xml-map "te_pce:SegmentIDValue";
      type uint32;
      description
        "Contains a SegmentID value in case SegmentID is
        valid";
    }
    leaf node-adjacency-id-exists {
      xr:xr-xml-map "te_pce:NodeAdjacencyIDExists";
      type boolean;
      description
        "If this flag is true, the bag contains
        NodeAdjacencyID information";
    }
    leaf node-id {
      xr:xr-xml-map "te_pce:NodeID";
      type inet:ipv4-address;
      description
        "Address of the node corresponding the node
        SegmentID";
    }
    leaf local-address {
      xr:xr-xml-map "te_pce:LocalAddress";
      type inet:ipv4-address;
      description
        "Address of the local address corresponding the
        adjacency SegmentID";
    }
    leaf remote-address {
      xr:xr-xml-map "te_pce:RemoteAddress";
      type inet:ipv4-address;
      description
        "Address of the remote address corresponding the
        adjacency SegmentID";
    }
  }

  grouping PCE-LSP-ROUTE-BAG {
    description "PCE LSP Route Object)";
    leaf is-used {
      xr:xr-xml-map "te_pce:IsUsed";
      type boolean;
      description "Route Object used flag";
    }
    leaf cost {
      xr:xr-xml-map "te_pce:Cost";
      type uint32;
      description "Cost";
    }
    leaf-list address {
      xr:xr-xml-map "te_pce:Addresses";
      type inet:ipv4-address;
      description "List of Addresses";
    }

    list subobject {
      description "List of Route Subobjects";
      uses PCE-LSP-ROUTE-HOP-BAG;
    }
  }

  grouping PCE-LSP-PATH-BAG {
    description "PCE LSP Path";

    container ero {
      description "Explicit Router Object";
      uses PCE-LSP-ROUTE-BAG;
    }

    container lspa {
      description "LSP Attributes Object";
      uses PCE-LSP-LSPA-BAG;
    }

    container rro {
      description "Reported Route Object";
      uses PCE-LSP-ROUTE-BAG;
    }
    leaf bw {
      xr:xr-xml-map "te_pce:Bw";
      type uint32;
      description "Bandwidth";
    }
    leaf is-bw-used {
      xr:xr-xml-map "te_pce:isBwUsed";
      type boolean;
      description "Bandwidth used flag";
    }
    leaf reopt-bw {
      xr:xr-xml-map "te_pce:ReoptBw";
      type uint32;
      description "Reoptimize bandwidth";
    }
    leaf is-reopt-bw-used {
      xr:xr-xml-map "te_pce:isReoptBwUsed";
      type boolean;
      description "Reoptimize bandwidth used flag";
    }

    list metric {
      description "List of Metrics";
      uses PCE-LSP-METRIC-BAG;
    }
  }

  grouping PCE-LSP-IDENTIFIERS-BAG {
    description "PCE LSP Identifiers TLV Information";
    leaf is-used {
      xr:xr-xml-map "te_pce:IsUsed";
      type boolean;
      description "LSP Identifier used flag";
    }
    leaf sender {
      xr:xr-xml-map "te_pce:Sender";
      type inet:ipv4-address;
      description "Sender Address";
    }
    leaf te-lsp-id {
      xr:xr-xml-map "te_pce:TeLspID";
      type uint16;
      description "TE LSP ID";
    }
    leaf tunnel-id {
      xr:xr-xml-map "te_pce:TunnelID";
      type uint16;
      description "LSPO Tunnel ID";
    }
    leaf ext-tunnel-id {
      xr:xr-xml-map "te_pce:ExtTunnelID";
      type uint32;
      description "External Tunnel ID";
    }
  }

  grouping PCE-LSP-PEER-BAG {
    description "PCE LSP Peer";
    leaf node-identifier {
      xr:xr-xml-map "te_pce:NodeIdentifier";
      type string;
      description "Peer Node Identifier";
    }
    leaf address {
      xr:xr-xml-map "te_pce:Address";
      type inet:ipv4-address;
      description "Peer Ip Address";
    }
  }

  grouping PCE-LSP-BAG {
    description "PCE LSP from LSP Database";

    container creator {
      description "Creator Peer of the LSP";
      uses PCE-LSP-PEER-BAG;
    }

    container delegated {
      description "Owner Peer of the LSP";
      uses PCE-LSP-PEER-BAG;
    }

    container identifiers {
      description "LSP Identifiers";
      uses PCE-LSP-IDENTIFIERS-BAG;
    }

    container autoroute {
      description "Auto Route";
      uses PCE-LSP-AUTOROUTE-BAG;
    }
    leaf error {
      xr:xr-xml-map "te_pce:Error";
      type string;
      description "Error (for display only)";
    }
    leaf source-address {
      xr:xr-xml-map "te_pce:SourceAddress";
      type inet:ipv4-address;
      description "Source IP Address";
    }
    leaf destination-address {
      xr:xr-xml-map "te_pce:DestinationAddress";
      type inet:ipv4-address;
      description "Destination IP Address";
    }
    leaf symbolic-name-xr {
      xr:xr-xml-map "te_pce:symbolic-name-xr";
      type string;
      description "Symbolic Name";
    }
    leaf session-internal-lsp-id {
      xr:xr-xml-map "te_pce:SessionInternalLspID";
      type uint32;
      description "Session internal ID";
    }
    leaf stateful-request-parameter-id {
      xr:xr-xml-map "te_pce:StatefulRequestParameterID";
      type uint32;
      description "SRP ID";
    }
    leaf request-queue-size {
      xr:xr-xml-map "te_pce:RequestQueueSize";
      type uint8;
      description "Request queue size";
    }
    leaf delegatable {
      xr:xr-xml-map "te_pce:Delegatable";
      type boolean;
      description "LSP delegatable";
    }
    leaf operational {
      xr:xr-xml-map "te_pce:Operational";
      type Pce-lsp-oper-state;
      description "LSP operational status";
    }
    leaf administrative {
      xr:xr-xml-map "te_pce:Administrative";
      type boolean;
      description "LSP administrative status";
    }
    leaf cleanup-timer-exp {
      xr:xr-xml-map "te_pce:CleanupTimerExp";
      type int32;
      description "Deprecated";
    }
    leaf delegation-timer-exp {
      xr:xr-xml-map "te_pce:DelegationTimerExp";
      type int32;
      description "LSP delegation timer expiration in sec";
    }
    leaf create {
      xr:xr-xml-map "te_pce:Create";
      type boolean;
      description "LSPO create flag";
    }
    leaf state-timer-exp {
      xr:xr-xml-map "te_pce:StateTimerExp";
      type int32;
      description "LSP state-timeout time expiration";
    }
    leaf lspo-is-used {
      xr:xr-xml-map "te_pce:LspoIsUsed";
      type boolean;
      description "LSP Object used flag";
    }
    leaf forward-class-id {
      xr:xr-xml-map "te_pce:ForwardClassID";
      type uint32;
      description "Forward Class ID";
    }
    leaf load-share {
      xr:xr-xml-map "te_pce:LoadShare";
      type uint32;
      description "Load share factor";
    }
    leaf delegation-status {
      xr:xr-xml-map "te_pce:DelegationStatus";
      type string;
      description "Delegation status";
    }
    leaf path-setup-type {
      xr:xr-xml-map "te_pce:PathSetupType";
      type uint8;
      description "Path setup type";
    }
    leaf binding-sid {
      xr:xr-xml-map "te_pce:BindingSID";
      type uint32;
      description "Binding SID";
    }
    leaf-list backup-path {
      xr:xr-xml-map "te_pce:BackupPath";
      type inet:ipv4-address;
      description "Backup Path";
    }

    list paths {
      description "Array of paths";
      uses PCE-LSP-PATH-BAG;
    }
  }
}
