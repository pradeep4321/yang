module Cisco-IOS-XR-mpls-te-oper {

  /*** NAMESPACE / PREFIX DEFINITION ***/

  namespace "http://cisco.com/ns/yang/Cisco-IOS-XR-mpls-te-oper";


  prefix "mpls-te-oper";

  /*** LINKAGE (IMPORTS / INCLUDES) ***/

  import ietf-inet-types { prefix "inet"; }

  import Cisco-IOS-XR-types { prefix "xr"; }

  include Cisco-IOS-XR-mpls-te-oper-sub9 {
    revision-date 2015-11-09;
  }

  include Cisco-IOS-XR-mpls-te-oper-sub8 {
    revision-date 2015-11-09;
  }

  include Cisco-IOS-XR-mpls-te-oper-sub7 {
    revision-date 2015-11-09;
  }

  include Cisco-IOS-XR-mpls-te-oper-sub6 {
    revision-date 2015-11-09;
  }

  include Cisco-IOS-XR-mpls-te-oper-sub5 {
    revision-date 2015-11-09;
  }

  include Cisco-IOS-XR-mpls-te-oper-sub4 {
    revision-date 2015-11-09;
  }

  include Cisco-IOS-XR-mpls-te-oper-sub3 {
    revision-date 2015-11-09;
  }

  include Cisco-IOS-XR-mpls-te-oper-sub2 {
    revision-date 2015-11-09;
  }

  include Cisco-IOS-XR-mpls-te-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR mpls-te package operational data.

     This module contains definitions
     for the following management objects:
       mpls-te: MPLS Traffic Engineering operational data
       mpls-lcac-standby: mpls lcac standby
       mpls-lcac: mpls lcac
       mpls-pce: mpls pce
       mpls-pce-stdby: mpls pce stdby
       mpls-tp: mpls tp
       mpls-te-standby: mpls te standby

     Copyright (c) 2013-2016 by Cisco Systems, Inc.
     All rights reserved.";

  revision "2015-11-09" {
    description
      "IOS XR 6.0 revision.";
  }

  typedef Attribute-set-name-length {
    type xr:Cisco-ios-xr-string {
      length "0..64";
    }
    description "Attribute set name length";
  }
  typedef Mpls-te-path {
    type enumeration {
      enum not-set {
        value 0;
        description "Not set";
      }
      enum dynamic {
        value 1;
        description "Dynamic";
      }
      enum explicit-name {
        value 3;
        description "Explicit name";
      }
      enum explicit-id {
        value 4;
        description "Explicit ID";
      }
      enum no-ero {
        value 5;
        description "No ERO";
      }
      enum segment-routing {
        value 6;
        description "Segment Routing";
      }
    }
    description "Mpls te path";
  }
  typedef Oc-mpls-te-tunnel {
    type enumeration {
      enum unknown {
        value 0;
        description "UNKNOWN";
      }
      enum p2p {
        value 1;
        description "P2P";
      }
      enum p2mp {
        value 2;
        description "P2MP";
      }
    }
    description "Oc mpls te tunnel";
  }
  typedef Mpls-te-node {
    type enumeration {
      enum router {
        value 1;
        description "Router";
      }
      enum network {
        value 2;
        description "Network";
      }
    }
    description "Mpls te node";
  }
  typedef Preemption-event-index-range {
    type uint32 {
      range "0..1999";
    }
    description "Preemption event index range";
  }
  typedef Mpls-pce-symbolic-name {
    type xr:Cisco-ios-xr-string {
      length "0..256";
    }
    description "Mpls pce symbolic name";
  }
  typedef Ctype {
    type enumeration {
      enum ctype-null {
        value 0;
        description "CTYPE NULL";
      }
      enum ctype-ipv4 {
        value 1;
        description "CTYPE IPV4";
      }
      enum ctype-ipv4-p2p-tunnel {
        value 7;
        description "CTYPE IPV4 P2P TUNNEL";
      }
      enum ctype-ipv6-p2p-tunnel {
        value 8;
        description "CTYPE IPV6 P2P TUNNEL";
      }
      enum ctype-ipv4-uni {
        value 9;
        description "CTYPE IPV4 UNI";
      }
      enum ctype-ipv4-p2mp-tunnel {
        value 13;
        description "CTYPE IPV4 P2MP TUNNEL";
      }
      enum ctype-ipv6-p2mp-tunnel {
        value 14;
        description "CTYPE IPV6 P2MP TUNNEL";
      }
    }
    description "Ctype";
  }
  typedef Mpls-te-next-hop {
    type enumeration {
      enum egress-resolve {
        value 0;
        description "Egress Resolve";
      }
      enum autoroute-dest {
        value 1;
        description "Autoroute Dest";
      }
    }
    description "Mpls te next hop";
  }
  typedef Mpls-te-attr-set {
    type enumeration {
      enum not-used {
        value 0;
        description "Not used";
      }
      enum static {
        value 1;
        description "Static";
      }
      enum lsp {
        value 2;
        description "LSP";
      }
      enum unassigned {
        value 3;
        description "Unassigned";
      }
      enum auto-backup {
        value 4;
        description "Auto backup";
      }
      enum auto-mesh {
        value 5;
        description "Auto mesh";
      }
      enum xro {
        value 6;
        description "XRO";
      }
      enum p2mp-te {
        value 7;
        description "P2MP TE";
      }
      enum otn-pp {
        value 8;
        description "OTN Path Protection";
      }
      enum p2p-te {
        value 9;
        description "P2P TE";
      }
    }
    description "Mpls te attr set";
  }
  typedef Mesh-group-id {
    type uint32 {
      range "0..4294967295";
    }
    description "Mesh group id";
  }
  typedef Mpls-te-igp-protocol {
    type enumeration {
      enum none {
        value 0;
        description "Not set";
      }
      enum isis {
        value 1;
        description "IS IS";
      }
      enum ospf {
        value 2;
        description "OSPF";
      }
    }
    description "Mpls te igp protocol";
  }

  grouping ADVERTISEMENTS {
    description "Common node of mpls-lcac, mpls-lcac-standby";

    container advertisements {
      xr:xr-xml-map "mpls_lcac_oper:Advertisements";
      description "The advertisement information in MPLS-LCAC";
      uses MPLS-LM-ADVERTISEMENT-INFO;
    }
  }

  grouping MAXIMUM-TUNNELS {
    description "Common node of mpls-te, mpls-te-standby";

    container maximum-tunnels {
      xr:xr-xml-map "mpls_te_oper:MaximumTunnels";
      description "MPLS Traffic Engineering Tunnels";
      uses TUNNEL-MAX-INFO;
    }
  }

  grouping ADMISSION-CONTROL {
    description "Common node of mpls-lcac, mpls-lcac-standby";

    container admission-control {
      xr:xr-xml-map "mpls_lcac_oper:AdmissionControl";
      description "The admission control information in MPLS-LCAC";

      container global {
        xr:xr-xml-map "mpls_lcac_oper:Global";
        description "The global admission control information";
        uses MPLS-LM-ADMISSION-CONTROL-COMMON-INFO;
      }

      container admitted-tunnels {
        xr:xr-xml-map "mpls_lcac_oper:AdmittedTunnelTable";
        description
          "The table of admitted tunnels information in
          MPLS-LCAC";

        list admitted-tunnel {
          xr:xr-xml-map "mpls_lcac_oper:AdmittedTunnel";
          key "source-address destination-port source-port"+
            " destination-address extended-tunnel-id"+
            " next-hop-address ctype p2mp-id";
          description
            "The information for a specific admitted tunnel";
          leaf source-address {
            xr:xr-xml-map "mpls_lcac_oper:SourceAddress";
            type inet:ipv4-address-no-zone;
            description "The source IP address of the tunnel";
          }
          leaf destination-port {
            xr:xr-xml-map "mpls_lcac_oper:DestinationPort";
            type int32;
            description "The tunnel number at the head";
          }
          leaf source-port {
            xr:xr-xml-map "mpls_lcac_oper:SourcePort";
            type int32;
            description
              "The signaling instance number of the tunnel";
          }
          leaf destination-address {
            xr:xr-xml-map "mpls_lcac_oper:DestinationAddress";
            type inet:ipv4-address-no-zone;
            description "The destination IP address of the tunnel";
          }
          leaf extended-tunnel-id {
            xr:xr-xml-map "mpls_lcac_oper:ExtendedTunnelID";
            type inet:ipv4-address-no-zone;
            description "Extended tunnel id";
          }
          leaf next-hop-address {
            xr:xr-xml-map "mpls_lcac_oper:NextHopAddress";
            type inet:ipv4-address-no-zone;
            description "The Next hop IP";
          }
          leaf ctype {
            xr:xr-xml-map "mpls_lcac_oper:Ctype";
            type Ctype;
            description "C type";
          }
          leaf p2mp-id {
            xr:xr-xml-map "mpls_lcac_oper:P2MP_ID";
            type int32;
            description "P2MP id";
          }
          uses MPLS-LM-ADMISSION-CONTROL-TUNNEL-INFO;
        }
      }

      container link-interfaces {
        xr:xr-xml-map "mpls_lcac_oper:LinkInterfaceTable";
        description
          "The global admission control information on
          Interfaces";

        list link-interface {
          xr:xr-xml-map "mpls_lcac_oper:LinkInterface";
          key "interface-name";
          description
            "The global admission control information on an
            interface";
          leaf interface-name {
            xr:xr-xml-map "mpls_lcac_oper:InterfaceName";
            type xr:Interface-name;
            description "Interface name";
          }
          uses MPLS-LM-ADMISSION-CONTROL-COMMON-INFO;
        }
      }
    }
  }

  grouping WRAP-PROTECTION {
    description "Common node of mpls-te, mpls-te-standby";

    container wrap-protection {
      xr:xr-xml-map "mpls_te_oper:WrapProtection";
      description
        "Represent all the LSP Wrap Protection info in
        MPLS-TE";

      container protected-lsps {
        xr:xr-xml-map "mpls_te_oper:ProtectedLSPTable";
        description
          "The set of wrap protected LSPs available in
          MPLS-TE";

        list protected-lsp {
          xr:xr-xml-map "mpls_te_oper:ProtectedLSP";
          key "source-address destination-address tunnel-id"+
            " extended-tunnel-id lsp-id sub-group-id"+
            " sub-group-originator p2mp-id session-type";
          description
            "Wrap protection info for a given protected LSP";
          leaf source-address {
            xr:xr-xml-map "mpls_te_oper:SourceAddress";
            type inet:ipv4-address-no-zone;
            description "Source Address";
          }
          leaf destination-address {
            xr:xr-xml-map "mpls_te_oper:DestinationAddress";
            type inet:ipv4-address-no-zone;
            description "Destination Address";
          }
          leaf tunnel-id {
            xr:xr-xml-map "mpls_te_oper:TunnelID";
            type int32;
            description "Tunnel ID";
          }
          leaf extended-tunnel-id {
            xr:xr-xml-map "mpls_te_oper:ExtendedTunnelID";
            type inet:ipv4-address-no-zone;
            description "Extended Tunnel ID";
          }
          leaf lsp-id {
            xr:xr-xml-map "mpls_te_oper:LSP_ID";
            type int32;
            description "LSP ID";
          }
          leaf sub-group-id {
            xr:xr-xml-map "mpls_te_oper:SubGroupID";
            type int32;
            description "Subgroup ID";
          }
          leaf sub-group-originator {
            xr:xr-xml-map "mpls_te_oper:SubGroupOriginator";
            type inet:ipv4-address-no-zone;
            description "Subgroup Orig ID";
          }
          leaf p2mp-id {
            xr:xr-xml-map "mpls_te_oper:P2MP_ID";
            type int32;
            description "P2MP ID";
          }
          leaf session-type {
            xr:xr-xml-map "mpls_te_oper:SessionType";
            type Ctype;
            description "Session Type";
          }
          uses MPLS-TE-LSP-WRAP-PROTECTION-BAG;
        }
      }
    }
  }

  grouping DIFF-SERV-TE-CLASSES {
    description "Common node of mpls-te, mpls-te-standby";

    container diff-serv-te-classes {
      xr:xr-xml-map "mpls_te_oper:DiffServTEClasses";
      description "The configured Diff Serv TE classes";
      uses MPLS-TE-DSTE-CLASSES;
    }
  }

  grouping PEER-TABLE {
    description "Common node of mpls-pce, mpls-pce-stdby";

    container peers {
      xr:xr-xml-map "te_pce_oper:PeerTable";
      description "The set of PCE peers";

      list peer {
        xr:xr-xml-map "te_pce_oper:Peer";
        key "peer-address";
        description "A PCE peer";
        leaf peer-address {
          xr:xr-xml-map "te_pce_oper:PeerAddress";
          type inet:ipv4-address-no-zone;
          description "The peer address";
        }
        uses PCE-NEIGHBOR-BAG;
      }
    }
  }

  grouping LINK-INFORMATION {
    description "Common node of mpls-lcac, mpls-lcac-standby";

    container link-information {
      xr:xr-xml-map "mpls_lcac_oper:LinkInformation";
      description "The interface information in MPLS-LCAC";

      container global {
        xr:xr-xml-map "mpls_lcac_oper:Global";
        description "The global information for all the interfaces";
        uses MPLS-LM-INTERFACE-COMMON-INFO;
      }

      container links {
        xr:xr-xml-map "mpls_lcac_oper:LinkTable";
        description "The table of interfaces in MPLS-LCAC";

        list link {
          xr:xr-xml-map "mpls_lcac_oper:Link";
          key "interface-name";
          description "An interface in MPLS-LCAC";
          leaf interface-name {
            xr:xr-xml-map "mpls_lcac_oper:InterfaceName";
            type xr:Interface-name;
            description "Interface name";
          }
          uses MPLS-LM-INTERFACE-LINK-INFO;
        }
      }
    }
  }

  grouping LSP-TABLE {
    description "Common node of mpls-pce, mpls-pce-stdby";

    container lsps {
      xr:xr-xml-map "te_pce_oper:LSPTable";
      description "Table of LSPs";

      list lsp {
        xr:xr-xml-map "te_pce_oper:LSP";
        key "symbolic-name";
        description "Information of a LSP from LSPDB";
        leaf symbolic-name {
          xr:xr-xml-map "te_pce_oper:SymbolicName";
          type Mpls-pce-symbolic-name;
          description "Symbolic name";
        }
        uses PCE-LSP-BAG;
      }
      uses PCE-LSP-BAG;
    }
  }

  grouping PREEMPTION-EVENT-TABLE {
    description "Common node of mpls-lcac, mpls-lcac-standby";

    container preemption-events {
      xr:xr-xml-map "mpls_lcac_oper:PreemptionEventTable";
      description "Preemption event log in MPLS-LCAC";

      list preemption-event {
        xr:xr-xml-map "mpls_lcac_oper:PreemptionEvent";
        key "event-index";
        description "Preemption event";
        leaf event-index {
          xr:xr-xml-map "mpls_lcac_oper:EventIndex";
          type Preemption-event-index-range;
          description "Event index";
        }
        uses MPLS-LM-PREEMPTION-EVENT;
      }
    }
  }

  grouping SIGNALLING-COUNTERS {
    description "Common node of mpls-te, mpls-te-standby";

    container signalling-counters {
      xr:xr-xml-map "mpls_te_oper:SignallingCounters";
      description "TE counters";

      container issu {
        xr:xr-xml-map "mpls_te_oper:ISSU";
        description "MPLS TE ISSU counters";
        uses MPLS-TE-SYNC-COUNT-INFO;
      }

      container heads-counters {
        xr:xr-xml-map "mpls_te_oper:HeadsCountersTable";
        description "MPLS TE counters signalling heads table";

        list heads-counter {
          xr:xr-xml-map "mpls_te_oper:HeadsCounter";
          key "tunnel-id";
          description "MPLS TE counters signalling head";
          leaf tunnel-id {
            xr:xr-xml-map "mpls_te_oper:TunnelID";
            type int32;
            description "tunnel id of last obtained tunnel";
          }
          uses TE-STATS-BAG-VIF;
        }
      }

      container mids-counters {
        xr:xr-xml-map "mpls_te_oper:MidsCountersTable";
        description "MPLS TE counters signalling heads table";

        list mids-counter {
          xr:xr-xml-map "mpls_te_oper:MidsCounter";
          key "source-address destination-address tunnel-id"+
            " extended-tunnel-id lsp-id";
          description "MPLS TE counters signalling mid";
          leaf source-address {
            xr:xr-xml-map "mpls_te_oper:SourceAddress";
            type inet:ipv4-address-no-zone;
            description "Source Address";
          }
          leaf destination-address {
            xr:xr-xml-map "mpls_te_oper:DestinationAddress";
            type inet:ipv4-address-no-zone;
            description "Destination Address";
          }
          leaf tunnel-id {
            xr:xr-xml-map "mpls_te_oper:TunnelID";
            type int32;
            description "tunnel id of last obtained tunnel";
          }
          leaf extended-tunnel-id {
            xr:xr-xml-map "mpls_te_oper:ExtendedTunnelID";
            type inet:ipv4-address-no-zone;
            description "Extended Tunnel ID";
          }
          leaf lsp-id {
            xr:xr-xml-map "mpls_te_oper:LSP_ID";
            type int32;
            description "LSP ID";
          }
          uses TE-STATS-BAG-LSP;
        }
      }

      container head-signalling-counters {
        xr:xr-xml-map "mpls_te_oper:HeadSignallingCountersTable";
        description "Sig Head Table TE counters";

        list head-signalling-counter {
          xr:xr-xml-map "mpls_te_oper:HeadSignallingCounters";
          key "ctype tunnel-id";
          description "TE stats";
          leaf ctype {
            xr:xr-xml-map "mpls_te_oper:CType";
            type Ctype;
            description "Ctype";
          }
          leaf tunnel-id {
            xr:xr-xml-map "mpls_te_oper:TunnelID";
            type int32;
            description "Tunnel ID";
          }
          uses TE-STATS-BAG-VIF;
        }
      }

      container remote-signalling-counters {
        xr:xr-xml-map "mpls_te_oper:RemoteSignallingCountersTable";
        description "Sig mid tail Table TE counters";

        list remote-signalling-counter {
          xr:xr-xml-map "mpls_te_oper:RemoteSignallingCounters";
          key "ctype tunnel-id extended-tunnel-id p2mp-id lsp-id"+
            " source-address destination-address"+
            " sub-group-originator sub-group-id";
          description "TE stats";
          leaf ctype {
            xr:xr-xml-map "mpls_te_oper:CType";
            type Ctype;
            description "Ctype";
          }
          leaf tunnel-id {
            xr:xr-xml-map "mpls_te_oper:TunnelID";
            type int32;
            description "Tunnel ID";
          }
          leaf extended-tunnel-id {
            xr:xr-xml-map "mpls_te_oper:ExtendedTunnelID";
            type inet:ipv4-address-no-zone;
            description "Extended Tunnel ID";
          }
          leaf p2mp-id {
            xr:xr-xml-map "mpls_te_oper:P2MP_ID";
            type int32;
            description "P2MP ID";
          }
          leaf lsp-id {
            xr:xr-xml-map "mpls_te_oper:LSP_ID";
            type int32;
            description "LSP ID";
          }
          leaf source-address {
            xr:xr-xml-map "mpls_te_oper:SourceAddress";
            type inet:ipv4-address-no-zone;
            description "Source Address";
          }
          leaf destination-address {
            xr:xr-xml-map "mpls_te_oper:DestinationAddress";
            type inet:ipv4-address-no-zone;
            description "Destination Address";
          }
          leaf sub-group-originator {
            xr:xr-xml-map "mpls_te_oper:SubGroupOriginator";
            type inet:ipv4-address-no-zone;
            description "Subgroup originator";
          }
          leaf sub-group-id {
            xr:xr-xml-map "mpls_te_oper:SubGroupID";
            type int32;
            description "Subgroup ID";
          }
          uses TE-STATS-BAG-LSP;
        }
      }

      container tails-counters {
        xr:xr-xml-map "mpls_te_oper:TailsCountersTable";
        description "MPLS TE counters signalling heads table";

        list tails-counter {
          xr:xr-xml-map "mpls_te_oper:TailsCounter";
          key "source-address destination-address tunnel-id"+
            " extended-tunnel-id lsp-id";
          description "MPLS TE counters signalling mid";
          leaf source-address {
            xr:xr-xml-map "mpls_te_oper:SourceAddress";
            type inet:ipv4-address-no-zone;
            description "Source Address";
          }
          leaf destination-address {
            xr:xr-xml-map "mpls_te_oper:DestinationAddress";
            type inet:ipv4-address-no-zone;
            description "Destination Address";
          }
          leaf tunnel-id {
            xr:xr-xml-map "mpls_te_oper:TunnelID";
            type int32;
            description "tunnel id of last obtained tunnel";
          }
          leaf extended-tunnel-id {
            xr:xr-xml-map "mpls_te_oper:ExtendedTunnelID";
            type inet:ipv4-address-no-zone;
            description "Extended Tunnel ID";
          }
          leaf lsp-id {
            xr:xr-xml-map "mpls_te_oper:LSP_ID";
            type int32;
            description "LSP ID";
          }
          uses TE-STATS-BAG-LSP;
        }
      }

      container signallings {
        xr:xr-xml-map "mpls_te_oper:SignallingCountersTable";
        description "TE counters";

        list signalling {
          xr:xr-xml-map "mpls_te_oper:Signalling";
          key "ctype tunnel-id extended-tunnel-id p2mp-id lsp-id"+
            " source-address destination-address"+
            " sub-group-originator sub-group-id";
          description "TE Sig";
          leaf ctype {
            xr:xr-xml-map "mpls_te_oper:CType";
            type Ctype;
            description "Ctype";
          }
          leaf tunnel-id {
            xr:xr-xml-map "mpls_te_oper:TunnelID";
            type int32;
            description "Tunnel ID";
          }
          leaf extended-tunnel-id {
            xr:xr-xml-map "mpls_te_oper:ExtendedTunnelID";
            type inet:ipv4-address-no-zone;
            description "Extended Tunnel ID";
          }
          leaf p2mp-id {
            xr:xr-xml-map "mpls_te_oper:P2MP_ID";
            type int32;
            description "P2MP ID";
          }
          leaf lsp-id {
            xr:xr-xml-map "mpls_te_oper:LSP_ID";
            type int32;
            description "LSP ID";
          }
          leaf source-address {
            xr:xr-xml-map "mpls_te_oper:SourceAddress";
            type inet:ipv4-address-no-zone;
            description "Source Address";
          }
          leaf destination-address {
            xr:xr-xml-map "mpls_te_oper:DestinationAddress";
            type inet:ipv4-address-no-zone;
            description "Destination Address";
          }
          leaf sub-group-originator {
            xr:xr-xml-map "mpls_te_oper:SubGroupOriginator";
            type inet:ipv4-address-no-zone;
            description "Subgroup originator";
          }
          leaf sub-group-id {
            xr:xr-xml-map "mpls_te_oper:SubGroupID";
            type int32;
            description "Subgroup ID";
          }
          uses TE-STATS-SIG-FILTER;
        }
      }

      container signalling-summary {
        xr:xr-xml-map "mpls_te_oper:SignallingSummary";
        description "Send-Recv count summary for TE Signaling";
        uses TE-STATS-SIG;
      }
    }
  }

  grouping OPEN-CONFIG {
    description "Common node of mpls-te, mpls-te-standby";

    container open-config {
      xr:xr-xml-map "oc_mpls_te_oper:OpenConfig";
      description "OpenConfig MPLS TE operational data";

      container lsp-states {
        xr:xr-xml-map "oc_mpls_te_oper:LSPStateTable";
        description "Table of LSP State Info";

        list lsp-state {
          xr:xr-xml-map "oc_mpls_te_oper:LSPState";
          key "tunnel-name tunnel-type";
          description "MPLS TE LSP State Info";
          leaf tunnel-name {
            xr:xr-xml-map "oc_mpls_te_oper:TunnelName";
            type xr:Cisco-ios-xr-string;
            description "Tunnel Name";
          }
          leaf tunnel-type {
            xr:xr-xml-map "oc_mpls_te_oper:TunnelType";
            type Oc-mpls-te-tunnel;
            description "Tunnel Type";
          }
          uses OC-MPLS-TE-LSP-STATE;
        }
      }

      container lsp-counters {
        xr:xr-xml-map "oc_mpls_te_oper:LSPCountersTable";
        description "Table of LSP Counters";

        list lsp-counter {
          xr:xr-xml-map "oc_mpls_te_oper:LSPCounters";
          key "tunnel-name tunnel-type";
          description "MPLS TE LSP Counters";
          leaf tunnel-name {
            xr:xr-xml-map "oc_mpls_te_oper:TunnelName";
            type xr:Cisco-ios-xr-string;
            description "Tunnel Name";
          }
          leaf tunnel-type {
            xr:xr-xml-map "oc_mpls_te_oper:TunnelType";
            type Oc-mpls-te-tunnel;
            description "Tunnel Type";
          }
          uses OC-MPLS-TE-LSP-COUNTERS;
        }
      }
    }
  }

  grouping STATISTICS {
    description "Common node of mpls-lcac, mpls-lcac-standby";

    container statistics {
      xr:xr-xml-map "mpls_lcac_oper:Statistics";
      description
        "The interface statistics information in
        MPLS-LCAC";

      container summary {
        xr:xr-xml-map "mpls_lcac_oper:Summary";
        description "The statistics summary for all interfaces";
        uses MPLS-LM-STATS-SUMMARY-INFO;
      }

      container statstics-links {
        xr:xr-xml-map "mpls_lcac_oper:StatisticsLinkTable";
        description
          "The table of statistics interfaces in MPLS-LCAC";

        list statstics-link {
          xr:xr-xml-map "mpls_lcac_oper:StatsticsLink";
          key "interface-name";
          description "An interface in MPLS-LCAC";
          leaf interface-name {
            xr:xr-xml-map "mpls_lcac_oper:InterfaceName";
            type xr:Interface-name;
            description "Interface name";
          }
          uses MPLS-LM-STATS-LINK-INFO;
        }
      }
    }
  }

  grouping TE-PCE-OPER-STATISTICS {
    description "Common node of mpls-pce, mpls-pce-stdby";

    container statistics {
      xr:xr-xml-map "te_pce_oper:Statistics";
      description "PCE stats info";
      uses PCE-STATS-BAG;
    }
  }

  grouping PATH-PROTECTION {
    description "Common node of mpls-te, mpls-te-standby";

    container path-protection {
      xr:xr-xml-map "mpls_te_oper:PathProtection";
      description "MPLS TE path protection info";

      container switchover-log {
        xr:xr-xml-map "mpls_te_oper:SwitchoverLog";
        description "MPLS TE path protection info";
        uses TE-PP-SW-LOG-BAG;
      }
    }
  }

  grouping ANNOUNCE-TUNNELS-INFO {
    description "Common node of mpls-te, mpls-te-standby";

    container announce-tunnels-info {
      xr:xr-xml-map "mpls_te_oper:AnnounceTunnelsInfo";
      description
        "Announced tunnels (forwarding adjacency and
        autoroute annonce)";

      container autoroute-announce-table {
        xr:xr-xml-map "mpls_te_oper:AutorouteAnnounceTable";
        description
          "Autoroute announce and forwarding adjacency
          table";
        uses ANNOUNCE-DEST;
      }

      container all-autoroute-table {
        xr:xr-xml-map "mpls_te_oper:AllAutorouteTable";
        description
          "Autoroute announce and forwarding adjacency
          table";
        uses ANNOUNCE-DEST;
      }
    }
  }

  grouping ATTRIBUTE-SET-TABLE {
    description "Common node of mpls-te, mpls-te-standby";

    container attribute-sets {
      xr:xr-xml-map "mpls_te_oper:AttributeSetTable";
      description "AttributeSet information.";

      list attribute-set {
        xr:xr-xml-map "mpls_te_oper:AttributeSet";
        key "attribute-set-type attribute-set-name";
        description "MPLS TE attribute-set information";
        leaf attribute-set-type {
          xr:xr-xml-map "mpls_te_oper:AttributeSetType";
          type Mpls-te-attr-set;
          description "Attribute Set Type";
        }
        leaf attribute-set-name {
          xr:xr-xml-map "mpls_te_oper:AttributeSetName";
          type Attribute-set-name-length;
          description "Attribute Set Name";
        }
        uses MPLS-TE-ATTRIBUTE-SET;
      }
    }
  }

  grouping ANNOUNCE-DEST {
    description
      "Common node of autoroute-announce-table,
      all-autoroute-table";

    list announce-dest {
      xr:xr-xml-map "mpls_te_oper:AnnounceDest";
      key "destination-address protocol area igp-id";
      description "Autoroute tunnels per destination information";
      leaf destination-address {
        xr:xr-xml-map "mpls_te_oper:DestinationAddress";
        type inet:ipv4-address-no-zone;
        description "Destination Address";
      }
      leaf protocol {
        xr:xr-xml-map "mpls_te_oper:Protocol";
        type Mpls-te-igp-protocol;
        description "The IGP protocol used by the tunnel";
      }
      leaf area {
        xr:xr-xml-map "mpls_te_oper:Area";
        type int32;
        description "Area";
      }
      leaf igp-id {
        xr:xr-xml-map "mpls_te_oper:IGP_ID";
        type xr:Cisco-ios-xr-string;
        description "IGP Instance ID";
      }
      uses MPLS-TE-ANNOUNCEMENT-DEST-BAG;
    }
  }

  grouping TOPOLOGY-BRIEF-TABLE {
    description "Common node of mpls-te, mpls-te-standby";

    container topology-briefs {
      xr:xr-xml-map "mpls_te_oper:TopologyBriefTable";
      description "MPLS-TE topology brief table";

      list topology-brief {
        xr:xr-xml-map "mpls_te_oper:TopologyBrief";
        key "protocol igp-id area topology-node-type igp-node-id";
        description "A node in MPLS-TE topoogy brief table";
        leaf protocol {
          xr:xr-xml-map "mpls_te_oper:Protocol";
          type Mpls-te-igp-protocol;
          description "IGP protocol type";
        }
        leaf igp-id {
          xr:xr-xml-map "mpls_te_oper:IGP_ID";
          type xr:Cisco-ios-xr-string;
          description "IGP instance";
        }
        leaf area {
          xr:xr-xml-map "mpls_te_oper:Area";
          type int32;
          description "IGP area";
        }
        leaf topology-node-type {
          xr:xr-xml-map "mpls_te_oper:TopologyNodeType";
          type Mpls-te-node;
          description "Node type";
        }
        leaf igp-node-id {
          xr:xr-xml-map "mpls_te_oper:IGPNodeID";
          type string;
          description "IGP Node ID";
        }
        uses MPLS-TE-TOPOLOGY-NODE;
      }
    }
  }

  grouping AUTO-TUNNEL {
    description "Common node of mpls-te, mpls-te-standby";

    container auto-tunnel {
      xr:xr-xml-map "mpls_te_autotunnel_oper:AutoTunnel";
      description "Auto tunnel information.";

      container pcc {
        xr:xr-xml-map "mpls_te_autotunnel_oper:PCC";
        description
          "Auto tunnel PCC (Path Computation Client)
          information.";

        container summary {
          xr:xr-xml-map "mpls_te_autotunnel_oper:Summary";
          description "MPLS TE auto-tunnel pcc summary information";
          uses MPLS-TE-AUTOTUN-PCC-SUMMARY-INFO;
        }
      }

      container mesh {
        xr:xr-xml-map "mpls_te_autotunnel_oper:Mesh";
        description "Auto tunnel mesh information.";

        container mesh-groups {
          xr:xr-xml-map "mpls_te_autotunnel_oper:MeshGroupTable";
          description "Display auto-tunnel mesh group";

          list mesh-group {
            xr:xr-xml-map "mpls_te_autotunnel_oper:MeshGroup";
            key "mesh-group-id";
            description
              "Display auto-tunnel mesh group information";
            leaf mesh-group-id {
              xr:xr-xml-map "mpls_te_autotunnel_oper:MeshGroupID";
              type Mesh-group-id;
              description "Mesh group ID";
            }
            uses MPLS-TE-MESHGROUP;
          }
        }

        container statistics {
          xr:xr-xml-map "mpls_te_autotunnel_oper:Statistics";
          description
            "MPLS TE auto-tunnel mesh counters (stats)
            information";
          uses TE-STATS-AUTOMESH;
        }

        container summary {
          xr:xr-xml-map "mpls_te_autotunnel_oper:Summary";
          description
            "MPLS TE auto-tunnel mesh summary information";
          uses MPLS-TE-AUTOTUN-MESH-SUMMARY-INFO;
        }

        container config {
          xr:xr-xml-map "mpls_te_autotunnel_oper:Config";
          description
            "MPLS TE auto-tunnel mesh configuration
            information";
          uses MPLS-TE-AUTOTUN-MESH-CONFIG-INFO;
        }

        container one-hop {
          xr:xr-xml-map "mpls_te_autotunnel_oper:OneHop";
          description "MPLS TE auto-tunnel mesh onehop information";

          container interfaces {
            xr:xr-xml-map "mpls_te_autotunnel_oper:InterfaceTable";
            description "Display auto-tunnel onehop interfaces";

            list interface {
              xr:xr-xml-map "mpls_te_autotunnel_oper:Interface";
              key "interface-name";
              description
                "Display auto-tunnel mesh onehop interface
                information";
              leaf interface-name {
                xr:xr-xml-map "mpls_te_autotunnel_oper:InterfaceNam"+
                  "e";
                type xr:Interface-name;
                description "Interface Name";
              }
              uses MPLS-TE-AUTOMESH-ONEHOP-INTERFACE;
            }
          }

          container statistics {
            xr:xr-xml-map "mpls_te_autotunnel_oper:Statistics";
            description
              "MPLS TE auto-tunnel mesh onehop counters
              (stats) information";
            uses TE-STATS-AUTOMESH;
          }

          container summary {
            xr:xr-xml-map "mpls_te_autotunnel_oper:Summary";
            description
              "MPLS TE auto-tunnel mesh onehop summary
              information";
            uses MPLS-TE-AUTOTUN-MESH-ONEHOP-SUMMARY-INFO;
          }
        }
      }

      container backup {
        xr:xr-xml-map "mpls_te_autotunnel_oper:Backup";
        description "Auto tunnel backup information.";

        container tunnels {
          xr:xr-xml-map "mpls_te_autotunnel_oper:TunnelTable";
          description "auto-tunnel backup information";

          list tunnel {
            xr:xr-xml-map "mpls_te_autotunnel_oper:Tunnel";
            key "backup-tunnel-name";
            description
              "Display auto tunnel backup tunnel information";
            leaf backup-tunnel-name {
              xr:xr-xml-map "mpls_te_autotunnel_oper:BackupTunnelNa"+
                "me";
              type xr:Cisco-ios-xr-string;
              description "Backup tunnel name";
            }
            uses MPLS-TE-AUTOTUN-BACKUP-TUNNEL-INFO;
          }
        }

        container statistics {
          xr:xr-xml-map "mpls_te_autotunnel_oper:Statistics";
          description
            "MPLS TE auto-tunnel backup counters (stats)
            information";
          uses TE-STATS-AUTOBACKUP;
        }

        container summary {
          xr:xr-xml-map "mpls_te_autotunnel_oper:Summary";
          description
            "MPLS TE auto-tunnel backup summary information";
          uses MPLS-TE-AUTOTUN-BACKUP-SUMMARY-INFO;
        }

        container config {
          xr:xr-xml-map "mpls_te_autotunnel_oper:Config";
          description
            "MPLS TE auto-tunnel backup configuration
            information";
          uses MPLS-TE-AUTOTUN-BACKUP-CONFIG-INFO;
        }
      }
    }
  }

  grouping COLLABORATOR-TIMERS {
    description "Common node of mpls-te, mpls-te-standby";

    container collaborator-timers {
      xr:xr-xml-map "mpls_te_oper:CollaboratorTimers";
      description "TE Collaborator timer status";
      uses MPLS-TE-P2MP-TIMERS-B;
    }
  }

  grouping SOFT-PREEMPTION {
    description "Common node of mpls-te, mpls-te-standby";

    container soft-preemption {
      xr:xr-xml-map "mpls_te_oper:SoftPreemption";
      description "Soft Preemption information.";

      container statistics {
        xr:xr-xml-map "mpls_te_oper:Statistics";
        description "MPLS TE soft preemption stats information";
        uses MPLS-TE-SOFT-PREEMPTION-STATS;
      }
    }
  }

  grouping P2P-P2MP-TUNNEL {
    description "Common node of mpls-te, mpls-te-standby";

    container p2p-p2mp-tunnel {
      xr:xr-xml-map "mpls_te_oper:P2P_P2MPTunnel";
      description "P2P or P2MP tunnels";

      container tunnel-remote-briefs {
        xr:xr-xml-map "mpls_te_oper:TunnelRemoteBriefTable";
        description
          "Restrict display to P2P or P2MP mid or tail
          tunnels";

        list tunnel-remote-brief {
          xr:xr-xml-map "mpls_te_oper:TunnelRemoteBrief";
          key "lsp-id tunnel-id extended-tunnel-id source-address"+
            " ctype destination-address p2mp-id";
          description "P2P or P2MP tunnel that is a mid or tail";
          leaf lsp-id {
            xr:xr-xml-map "mpls_te_oper:LSP_ID";
            type int32;
            description "LSP ID";
          }
          leaf tunnel-id {
            xr:xr-xml-map "mpls_te_oper:TunnelID";
            type int32;
            description "Tunnel ID";
          }
          leaf extended-tunnel-id {
            xr:xr-xml-map "mpls_te_oper:ExtendedTunnelID";
            type inet:ipv4-address-no-zone;
            description "Extended Tunnel ID";
          }
          leaf source-address {
            xr:xr-xml-map "mpls_te_oper:SourceAddress";
            type inet:ipv4-address-no-zone;
            description "Source Address";
          }
          leaf ctype {
            xr:xr-xml-map "mpls_te_oper:CType";
            type Ctype;
            description "Ctype";
          }
          leaf destination-address {
            xr:xr-xml-map "mpls_te_oper:DestinationAddress";
            type inet:ipv4-address-no-zone;
            description "Destination Address";
          }
          leaf p2mp-id {
            xr:xr-xml-map "mpls_te_oper:P2MP_ID";
            type int32;
            description "P2MP ID";
          }
          uses MPLS-TE-P2MP-LSP-BRIEF;
        }
      }

      container tunnel-remotes {
        xr:xr-xml-map "mpls_te_oper:TunnelRemoteTable";
        description
          "Restrict display to P2P or P2MP mid or tail
          tunnels";

        list tunnel-remote {
          xr:xr-xml-map "mpls_te_oper:TunnelRemote";
          key "lsp-id tunnel-id extended-tunnel-id source-address"+
            " ctype destination-address p2mp-id";
          description "P2P or P2MP tunnel that is a mid or tail";
          leaf lsp-id {
            xr:xr-xml-map "mpls_te_oper:LSP_ID";
            type int32;
            description "LSP ID";
          }
          leaf tunnel-id {
            xr:xr-xml-map "mpls_te_oper:TunnelID";
            type int32;
            description "Tunnel ID";
          }
          leaf extended-tunnel-id {
            xr:xr-xml-map "mpls_te_oper:ExtendedTunnelID";
            type inet:ipv4-address-no-zone;
            description "Extended Tunnel ID";
          }
          leaf source-address {
            xr:xr-xml-map "mpls_te_oper:SourceAddress";
            type inet:ipv4-address-no-zone;
            description "Source Address";
          }
          leaf ctype {
            xr:xr-xml-map "mpls_te_oper:CType";
            type Ctype;
            description "Ctype";
          }
          leaf destination-address {
            xr:xr-xml-map "mpls_te_oper:DestinationAddress";
            type inet:ipv4-address-no-zone;
            description "Destination Address";
          }
          leaf p2mp-id {
            xr:xr-xml-map "mpls_te_oper:P2MP_ID";
            type int32;
            description "P2MP ID";
          }
          uses MPLS-TE-P2MP-LSP;
        }
      }

      container nni-tunnels {
        xr:xr-xml-map "mpls_te_oper:NNITunnelTable";
        description "GMPLS NNI tunnels";

        list nni-tunnel {
          xr:xr-xml-map "mpls_te_oper:NNITunnel";
          key "tunnel-id source-address destination-address";
          description "GMPLS-NNI tail tunnel";
          leaf tunnel-id {
            xr:xr-xml-map "mpls_te_oper:TunnelID";
            type int32;
            description "Tunnel ID";
          }
          leaf source-address {
            xr:xr-xml-map "mpls_te_oper:SourceAddress";
            type inet:ipv4-address-no-zone;
            description "Source Address";
          }
          leaf destination-address {
            xr:xr-xml-map "mpls_te_oper:DestinationAddress";
            type inet:ipv4-address-no-zone;
            description "Destination Address";
          }
          uses MPLS-TE-P2MP-TUNNEL-BAG;
        }
      }

      container tunnel-heads {
        xr:xr-xml-map "mpls_te_oper:TunnelHeadTable";
        description "Restrict display to P2P or P2MP head tunnels";

        list tunnel-head {
          xr:xr-xml-map "mpls_te_oper:TunnelHead";
          key "tunnel-name";
          description "mpls te p2p or p2mp tunnels";
          leaf tunnel-name {
            xr:xr-xml-map "mpls_te_oper:TunnelName";
            type xr:Cisco-ios-xr-string;
            description "Tunnel Name";
          }
          uses MPLS-TE-P2MP-TUNNEL-BAG;
        }
      }
    }
  }

  grouping BFD-NEIGHBOR-TABLE {
    description "Common node of mpls-lcac, mpls-lcac-standby";

    container bfd-neighbors {
      xr:xr-xml-map "mpls_lcac_oper:BFDNeighborTable";
      description "BFD Neighbors";

      list bfd-neighbor {
        xr:xr-xml-map "mpls_lcac_oper:BFDNeighbor";
        key "interface-name";
        description "A BFD Neighbor";
        leaf interface-name {
          xr:xr-xml-map "mpls_lcac_oper:InterfaceName";
          type xr:Interface-name;
          description "Interface name";
        }
        uses MPLS-LM-BFD-NBRS-LINK-INFO;
      }
    }
  }

  grouping SOFT-PREEMPTION-TABLE {
    description "Common node of mpls-lcac, mpls-lcac-standby";

    container soft-preemptions {
      xr:xr-xml-map "mpls_lcac_oper:SoftPreemptionTable";
      description
        "The soft preemption information for the TE-links";

      list soft-preemption {
        xr:xr-xml-map "mpls_lcac_oper:SoftPreemption";
        key "interface-name";
        description "The soft preemption info for a TE-link";
        leaf interface-name {
          xr:xr-xml-map "mpls_lcac_oper:InterfaceName";
          type xr:Interface-name;
          description "Interface name";
        }
        uses MPLS-LM-SOFT-PREEMPTION-LINK-INFO;
      }
    }
  }

  grouping TUNNEL-TABLE {
    description "Common node of mpls-pce, mpls-pce-stdby";

    container tunnels {
      xr:xr-xml-map "te_pce_oper:TunnelTable";
      description "Table of PCE tunnels";

      list tunnel {
        xr:xr-xml-map "te_pce_oper:Tunnel";
        key "tunnel-name";
        description "Information of a PCE tunnel";
        leaf tunnel-name {
          xr:xr-xml-map "te_pce_oper:TunnelName";
          type xr:Cisco-ios-xr-string;
          description "Tunnel Name";
        }
        uses PCE-TUNNEL-BAG;
      }
      uses PCE-TUNNEL-BAG;
    }
  }

  grouping FAST-REROUTE {
    description "Common node of mpls-te, mpls-te-standby";

    container fast-reroute {
      xr:xr-xml-map "mpls_te_oper:FastReroute";
      description "Represent all the fastreroute info in MPLS-TE";

      container backup-tunnels {
        xr:xr-xml-map "mpls_te_oper:BackupTunnelTable";
        description
          "The set of fastreroute backup tunnels available
          in MPLS-TE";

        list backup-tunnel {
          xr:xr-xml-map "mpls_te_oper:BackupTunnel";
          key "tunnel-name interface-name";
          description "Fastreroute info for a given backup tunnel";
          leaf tunnel-name {
            xr:xr-xml-map "mpls_te_oper:TunnelName";
            type xr:Cisco-ios-xr-string;
            description "Backup tunnel name";
          }
          leaf interface-name {
            xr:xr-xml-map "mpls_te_oper:InterfaceName";
            type xr:Interface-name;
            description "Protected interface name";
          }
          uses MPLS-TE-FASTREROUTE-BAG;
        }
      }

      container protected-interfaces {
        xr:xr-xml-map "mpls_te_oper:ProtectedInterfaceTable";
        description
          "The set of fastreroute protected interfaces
          available in MPLS-TE";

        list protected-interface {
          xr:xr-xml-map "mpls_te_oper:ProtectedInterface";
          key "interface-name backup-tunnel-name";
          description
            "Fastreroute info for a given protected
            interface";
          leaf interface-name {
            xr:xr-xml-map "mpls_te_oper:InterfaceName";
            type xr:Interface-name;
            description "Protected interface name";
          }
          leaf backup-tunnel-name {
            xr:xr-xml-map "mpls_te_oper:BackupTunnelName";
            type xr:Cisco-ios-xr-string;
            description "Backup tunnel name";
          }
          uses MPLS-TE-FASTREROUTE-BAG;
        }
      }

      container protections {
        xr:xr-xml-map "mpls_te_oper:ProtectionTable";
        description
          "The set of fastreroute protected interfaces
          available in MPLS-TE";

        list protection {
          xr:xr-xml-map "mpls_te_oper:Protection";
          key "source-address destination-address tunnel-id"+
            " extended-tunnel-id lsp-id sub-group-id"+
            " sub-group-originator p2mp-id session-type";
          description
            "Fastreroute info for a given protection
            interface";
          leaf source-address {
            xr:xr-xml-map "mpls_te_oper:SourceAddress";
            type inet:ipv4-address-no-zone;
            description "Source Address";
          }
          leaf destination-address {
            xr:xr-xml-map "mpls_te_oper:DestinationAddress";
            type inet:ipv4-address-no-zone;
            description "Destination Address";
          }
          leaf tunnel-id {
            xr:xr-xml-map "mpls_te_oper:TunnelID";
            type int32;
            description "Tunnel ID";
          }
          leaf extended-tunnel-id {
            xr:xr-xml-map "mpls_te_oper:ExtendedTunnelID";
            type inet:ipv4-address-no-zone;
            description "Extended Tunnel ID";
          }
          leaf lsp-id {
            xr:xr-xml-map "mpls_te_oper:LSP_ID";
            type int32;
            description "LSP ID";
          }
          leaf sub-group-id {
            xr:xr-xml-map "mpls_te_oper:SubGroupID";
            type int32;
            description "Subgroup ID";
          }
          leaf sub-group-originator {
            xr:xr-xml-map "mpls_te_oper:SubGroupOriginator";
            type inet:ipv4-address-no-zone;
            description "Subgroup Orig ID";
          }
          leaf p2mp-id {
            xr:xr-xml-map "mpls_te_oper:P2MP_ID";
            type int32;
            description "P2MP ID";
          }
          leaf session-type {
            xr:xr-xml-map "mpls_te_oper:SessionType";
            type int32;
            description "Session Type";
          }
          uses MPLS-TE-FASTREROUTE-PROTECTION-BAG;
        }
      }

      container promotion {
        xr:xr-xml-map "mpls_te_oper:Promotion";
        description
          "The info about the promotion timer of backup
          tunnels";
        uses MPLS-TE-FASTREROUTE-PROMOTION-BAG;
      }
    }
  }

  grouping TOPOLOGY {
    description "Common node of mpls-te, mpls-te-standby";

    container topology {
      xr:xr-xml-map "mpls_te_oper:Topology";
      description "The topology information in MPLS-TE";

      container global {
        xr:xr-xml-map "mpls_te_oper:Global";
        description
          "Global information about the overall MPLS-TE
          topology";
        uses MPLS-TE-TOPOLOGY-GLOBAL-INFO-BAG;
      }

      container destination-paths {
        xr:xr-xml-map "mpls_te_oper:DestinationPathTable";
        description
          "This table models the path calculation
          capabilities in MPLS-TE.A GET operation for the
          complete table will return no entries.See the
          class DestinationPath for more details.";

        list destination-path {
          xr:xr-xml-map "mpls_te_oper:DestinationPath";
          description
            "A GET operation on this class returns the best
            available path in the TE topology to reach the
            specified destination while satisfying the
            specified constraints.";
          leaf destination-address {
            xr:xr-xml-map "mpls_te_oper:DestinationAddress";
            type inet:ipv4-address-no-zone;
            description "Destination Address";
          }
          leaf affinity-bits {
            xr:xr-xml-map "mpls_te_oper:AffinityBits";
            type int32;
            description "Affinity Bits";
          }
          leaf affinity-mask {
            xr:xr-xml-map "mpls_te_oper:AffinityMask";
            type int32;
            description "Affinity Mask";
          }
          leaf setup-priority {
            xr:xr-xml-map "mpls_te_oper:SetupPriority";
            type int32;
            description "Setup Priority";
          }
          leaf hold-priority {
            xr:xr-xml-map "mpls_te_oper:HoldPriority";
            type int32;
            description "Hold Priority";
          }
          leaf bandwidth {
            xr:xr-xml-map "mpls_te_oper:Bandwidth";
            type int32;
            units "kbit/s";
            description "Bandwidth in kbps";
          }
          leaf igp-type {
            xr:xr-xml-map "mpls_te_oper:IGPType";
            type Mpls-te-igp-protocol;
            description "IGP Type";
          }
          leaf igp-instance {
            xr:xr-xml-map "mpls_te_oper:IGPInstance";
            type xr:Cisco-ios-xr-string;
            description "IGP Instance";
          }
          leaf igp-area {
            xr:xr-xml-map "mpls_te_oper:IGPArea";
            type int32;
            description "IGP Area";
          }
          leaf hop-limit {
            xr:xr-xml-map "mpls_te_oper:HopLimit";
            type int32;
            description "Hop Limit";
          }
          leaf exclude-srlg-ip-address {
            xr:xr-xml-map "mpls_te_oper:ExcludeSRLGIPAddress";
            type inet:ipv4-address-no-zone;
            description "Exclude SRLG IP Address";
          }
          leaf path-type {
            xr:xr-xml-map "mpls_te_oper:PathType";
            type Mpls-te-path;
            description "Path Type";
          }
          leaf path-id {
            xr:xr-xml-map "mpls_te_oper:PathID";
            type int32;
            description
              "This is the ID of the explicit path to be
              used for this path calculation query";
          }
          leaf path-name {
            xr:xr-xml-map "mpls_te_oper:PathName";
            type xr:Cisco-ios-xr-string;
            description
              "This is the name of the explicit path to be
              used for this path calculation query";
          }
          leaf cost-limit {
            xr:xr-xml-map "mpls_te_oper:CostLimit";
            type int32;
            description "Cost Limit";
          }
          uses MPLS-TE-TOPOLOGY-PATH-BAG;
        }
      }

      container configured-srlgs {
        xr:xr-xml-map "mpls_te_oper:ConfiguredSRLGTable";
        description "Set of configured SRLG";

        list configured-srlg {
          xr:xr-xml-map "mpls_te_oper:ConfiguredSRLG";
          key "srlg-number";
          description
            "Configured SRLG value and the addresses using
            it";
          leaf srlg-number {
            xr:xr-xml-map "mpls_te_oper:SRLGNumber";
            type int32;
            description "SRLG Number";
          }
          uses MPLS-TE-TOPO-CFG-SRLG;
        }
      }

      container srlgs {
        xr:xr-xml-map "mpls_te_oper:SRLGTable";
        description
          "Set of SRLG operational value for the overall
          MPLS-TE topology";

        list srlg {
          xr:xr-xml-map "mpls_te_oper:SRLG";
          key "srlg-number";
          description
            "SRLG operational value for the overall MPLS-TE
            topology";
          leaf srlg-number {
            xr:xr-xml-map "mpls_te_oper:SRLGNumber";
            type int32;
            description "SRLG Number";
          }
          uses MPLS-TE-TOPO-SRLG;
        }
      }

      container path-tunnels {
        xr:xr-xml-map "mpls_te_oper:TopologyPath";
        description "MPLS-Te topology path info";

        list path-tunnel {
          xr:xr-xml-map "mpls_te_oper:PathTunnel";
          description
            "MPLS-TE topology path taken by the specified
            tunnel";
          leaf tunnel-id {
            xr:xr-xml-map "mpls_te_oper:TunnelID";
            type int32;
            description "Tunnel ID";
          }
          leaf tunnel-name {
            xr:xr-xml-map "mpls_te_oper:TunnelName";
            type xr:Cisco-ios-xr-string;
            description "Tunnel name";
          }
          uses MPLS-TE-TOPOLOGY-PATH-BAG;
        }
      }
    }
  }

  grouping TE-PCE-OPER-TOPOLOGY {
    description "Common node of mpls-pce, mpls-pce-stdby";

    container topology {
      xr:xr-xml-map "te_pce_oper:Topology";
      description "The topology information in PCE";

      container global {
        xr:xr-xml-map "te_pce_oper:Global";
        description
          "The global information of the overall  topology";
        uses PCE-TOPOLOGY-GLOBAL-INFO-BAG;
      }
    }
  }

  grouping FORWARDING-ADJACENCY-DESTINATION-TABLE {
    description "Common node of mpls-te, mpls-te-standby";

    container forwarding-adjacency-destinations {
      xr:xr-xml-map "mpls_te_oper:ForwardingAdjacencyDestinationTab"+
        "le";
      description "Announced Destination tunnel";

      list forwarding-adjacency-destination {
        xr:xr-xml-map "mpls_te_oper:ForwardingAdjacencyDestination";
        key "destination-address";
        description "Forwarding Adjacencies for a destination";
        leaf destination-address {
          xr:xr-xml-map "mpls_te_oper:DestinationAddress";
          type inet:ipv4-address-no-zone;
          description "Destination address";
        }
        uses MPLS-TE-FWD-ADJ-BAG;
      }
    }
  }

  grouping LINK-SUMMARY {
    description "Common node of mpls-lcac, mpls-lcac-standby";

    container link-summary {
      xr:xr-xml-map "mpls_lcac_oper:LinkSummary";
      description "The global summary for all the interfaces";
      uses MPLS-LM-SUMMARY-COMMON-INFO;
    }
  }

  grouping BANDWIDTH-ALLOCATION {
    description "Common node of mpls-lcac, mpls-lcac-standby";

    container bandwidth-allocation {
      xr:xr-xml-map "mpls_lcac_oper:BandwidthAllocation";
      description
        "The bandwidth allocation information in
        MPLS-LCAC";

      container global {
        xr:xr-xml-map "mpls_lcac_oper:Global";
        description
          "Global bandwidth allocation information for all
          interfaces";
        uses MPLS-LM-BW-ALLOC-COMMON-INFO;
      }

      container bandwidth-allocation-links {
        xr:xr-xml-map "mpls_lcac_oper:BandwidthAllocationLinkTable";
        description
          "Per-link bandwidth allocation information in
          MPLS-LCAC";

        list bandwidth-allocation-link {
          xr:xr-xml-map "mpls_lcac_oper:BandwidthAllocationLink";
          key "interface-name";
          description
            "The bandwidth allocation for a given interface";
          leaf interface-name {
            xr:xr-xml-map "mpls_lcac_oper:InterfaceName";
            type xr:Interface-name;
            description "Interface name";
          }
          uses MPLS-LM-BW-ALLOC-LINK-INFO;
        }
      }
    }
  }

  grouping TUNNELS {
    description "Common node of mpls-te, mpls-te-standby";

    container tunnels {
      xr:xr-xml-map "mpls_te_oper:Tunnels";
      description "Failure protection provided for tunnels";

      container tunnel-flex-lsps {
        xr:xr-xml-map "mpls_te_oper:TunnelFlexLSPTable";
        description "Flex LSP";

        list tunnel-flex-lsp {
          xr:xr-xml-map "mpls_te_oper:TunnelFlexLSP";
          description "Flex LSP";
          leaf ctype {
            xr:xr-xml-map "mpls_te_oper:CType";
            type Ctype;
            description "Ctype";
          }
          leaf tunnel-id {
            xr:xr-xml-map "mpls_te_oper:TunnelID";
            type int32;
            description "Tunnel ID";
          }
          leaf tunnel-name {
            xr:xr-xml-map "mpls_te_oper:TunnelName";
            type xr:Cisco-ios-xr-string;
            description "Tunnel Name";
          }
          uses MPLS-TE-FLEX-LSP;
        }
      }

      container tunnel-auto-bandwidths {
        xr:xr-xml-map "mpls_te_oper:TunnelAutoBandwidthTable";
        description "Auto Bandwidth";

        list tunnel-auto-bandwidth {
          xr:xr-xml-map "mpls_te_oper:TunnelAutoBandwidth";
          key "tunnel-name";
          description "Auto Bandwidth info bag";
          leaf tunnel-name {
            xr:xr-xml-map "mpls_te_oper:TunnelName";
            type xr:Cisco-ios-xr-string;
            description "Tunnel Name";
          }
          uses MPLS-TE-TUNNELS-AUTOBW-BRIEF;
        }
      }

      container tunnel-auto-bandwidth-tunnels {
        xr:xr-xml-map "mpls_te_oper:TunnelAutoBandwidthTunnelTable";
        description "Auto Bandwidth";

        list tunnel-auto-bandwidth-tunnel {
          xr:xr-xml-map "mpls_te_oper:TunnelAutoBandwidthTunnel";
          key "source-address destination-address";
          description "Auto Bandwidth info bag";
          leaf source-address {
            xr:xr-xml-map "mpls_te_oper:SourceAddress";
            type inet:ipv4-address-no-zone;
            description "Source Address";
          }
          leaf destination-address {
            xr:xr-xml-map "mpls_te_oper:DestinationAddress";
            type inet:ipv4-address-no-zone;
            description "Destination Address";
          }
          uses MPLS-TE-TUNNELS-AUTOBW-BRIEF;
        }
      }

      container summary {
        xr:xr-xml-map "mpls_te_oper:Summary";
        description "Summary of tunnel info";
        uses MPLS-TE-TUNNELS-SUMMARY-INFO-BAG;
      }

      container tunnel-path-protections {
        xr:xr-xml-map "mpls_te_oper:TunnelPathProtectionTable";
        description "Path protection";

        list tunnel-path-protection {
          xr:xr-xml-map "mpls_te_oper:TunnelPathProtection";
          description "Path Protection";
          leaf ctype {
            xr:xr-xml-map "mpls_te_oper:CType";
            type Ctype;
            description "Ctype";
          }
          leaf tunnel-id {
            xr:xr-xml-map "mpls_te_oper:TunnelID";
            type int32;
            description "Tunnel ID";
          }
          leaf tunnel-name {
            xr:xr-xml-map "mpls_te_oper:TunnelName";
            type xr:Cisco-ios-xr-string;
            description "Tunnel Name";
          }
          uses MPLS-TE-PATH-PROTECTION;
        }
      }
    }
  }

  grouping IGP-AREA-BRIEF-TABLE {
    description "Common node of mpls-te, mpls-te-standby";

    container igp-area-briefs {
      xr:xr-xml-map "mpls_te_oper:IGPAreaBriefTable";
      description "The set of IGP-areas known to MPLS-TE";

      list igp-area-brief {
        xr:xr-xml-map "mpls_te_oper:IGPAreaBrief";
        key "protocol process-tag";
        description "An IGP instance Brief info";
        leaf protocol {
          xr:xr-xml-map "mpls_te_oper:Protocol";
          type Mpls-te-igp-protocol;
          description "The IGP protocol";
        }
        leaf process-tag {
          xr:xr-xml-map "mpls_te_oper:ProcessTag";
          type xr:Cisco-ios-xr-string;
          description "IGP Process Tag";
        }
        uses TE-SH-IGP;
      }
    }
  }

  grouping IGP-AREA-TABLE {
    description "Common node of mpls-te, mpls-te-standby";

    container igp-areas {
      xr:xr-xml-map "mpls_te_oper:IGPAreaTable";
      description "The set of IGP-areas known to MPLS-TE";

      list igp-area {
        xr:xr-xml-map "mpls_te_oper:IGPArea";
        key "protocol process-tag";
        description "An IGP instance";
        leaf protocol {
          xr:xr-xml-map "mpls_te_oper:Protocol";
          type Mpls-te-igp-protocol;
          description "The IGP protocol";
        }
        leaf process-tag {
          xr:xr-xml-map "mpls_te_oper:ProcessTag";
          type xr:Cisco-ios-xr-string;
          description "IGP Process Tag";
        }
        uses TE-SH-IGP;
      }
    }
  }

  grouping P2MP {
    description "Common node of mpls-te, mpls-te-standby";

    container p2mp {
      xr:xr-xml-map "mpls_te_oper:P2MP";
      description "P2MP Information";

      container tunnel-rewrites {
        xr:xr-xml-map "mpls_te_oper:TunnelRewriteTable";
        description "forwarding-adjacency P2MP Tunnel RW";

        list tunnel-rewrite {
          xr:xr-xml-map "mpls_te_oper:TunnelRewrite";
          key "tunnel-id lsp-id ctype";
          description "Display only P2MP Information";
          leaf tunnel-id {
            xr:xr-xml-map "mpls_te_oper:TunnelID";
            type int32;
            description "Tunnel ID";
          }
          leaf lsp-id {
            xr:xr-xml-map "mpls_te_oper:LSP_ID";
            type int32;
            description "LSP ID";
          }
          leaf ctype {
            xr:xr-xml-map "mpls_te_oper:CType";
            type Ctype;
            description "Ctype";
          }
          uses MPLS-TE-S2L-TUN-RW-BAG;
        }
      }

      container collaborator-timers {
        xr:xr-xml-map "mpls_te_oper:CollaboratorTimers";
        description "TE Collaborator timer status";
        uses MPLS-TE-P2MP-TIMERS-B;
      }

      container forwarding-output-label-rewrites {
        xr:xr-xml-map "mpls_te_oper:ForwardingOutputLabelRewriteTab"+
          "le";
        description "forwarding-adjacency P2MP Information";

        list forwarding-output-label-rewrite {
          xr:xr-xml-map "mpls_te_oper:ForwardingOutputLabelRewrite";
          key "tunnel-id lsp-id extended-tunnel-id source-address"+
            " p2mp-id destination-address next-hop-address"+
            " previous-hop-address ctype";
          description "Display only P2MP Information";
          leaf tunnel-id {
            xr:xr-xml-map "mpls_te_oper:TunnelID";
            type int32;
            description "Tunnel ID";
          }
          leaf lsp-id {
            xr:xr-xml-map "mpls_te_oper:LSP_ID";
            type int32;
            description "LSP ID";
          }
          leaf extended-tunnel-id {
            xr:xr-xml-map "mpls_te_oper:ExtendedTunnelID";
            type inet:ipv4-address-no-zone;
            description "extended tunnel ID";
          }
          leaf source-address {
            xr:xr-xml-map "mpls_te_oper:SourceAddress";
            type inet:ipv4-address-no-zone;
            description "Source Address";
          }
          leaf p2mp-id {
            xr:xr-xml-map "mpls_te_oper:P2MP_ID";
            type int32;
            description "P2MP ID";
          }
          leaf destination-address {
            xr:xr-xml-map "mpls_te_oper:DestinationAddress";
            type inet:ipv4-address-no-zone;
            description "Destination Address";
          }
          leaf next-hop-address {
            xr:xr-xml-map "mpls_te_oper:NextHopAddress";
            type inet:ipv4-address-no-zone;
            description "Next Hop";
          }
          leaf previous-hop-address {
            xr:xr-xml-map "mpls_te_oper:PreviousHopAddress";
            type inet:ipv4-address-no-zone;
            description "Prev Hop";
          }
          leaf ctype {
            xr:xr-xml-map "mpls_te_oper:CType";
            type Ctype;
            description "Ctype";
          }
          uses MPLS-TE-S2L-FORWARDING-BAG;
        }
      }
    }
  }

  grouping NSR {
    description "Common node of mpls-te, mpls-te-standby";

    container nsr {
      xr:xr-xml-map "mpls_te_oper:NSR";
      description "MPLS TE NSR information";

      container status {
        xr:xr-xml-map "mpls_te_oper:Status";
        description "MPLS TE NSR Status information";
        uses TE-NSR-ISSU-STATUS-INFO;
      }

      container detail {
        xr:xr-xml-map "mpls_te_oper:Detail";
        description "MPLS TE NSR Status information";
        uses TE-NSR-ISSU-STATUS-INFO;
      }
    }
  }

  grouping AFFINITY-MAP {
    description "Common node of mpls-te, mpls-te-standby";

    container affinity-map {
      xr:xr-xml-map "mpls_te_oper:AffinityMap";
      description "Affinity name to value mapping";
      uses MPLS-TE-AFFINITY-MAP-BAG;
    }
  }

  grouping BFD {
    description "Common node of mpls-te, mpls-te-standby";

    container bfd {
      xr:xr-xml-map "mpls_te_oper:BFD";
      description "MPLS TE BFD Oper Info";

      container head-infos {
        xr:xr-xml-map "mpls_te_oper:P2PHeadInfoTable";
        description "MPLS TE Head BFD Over LSP Table";

        list head-info {
          xr:xr-xml-map "mpls_te_oper:HeadInfo";
          key "tunnel-name";
          description "MPLS TE Head End BFD Over LSP Info";
          leaf tunnel-name {
            xr:xr-xml-map "mpls_te_oper:TunnelName";
            type xr:Cisco-ios-xr-string;
            description "Tunnel Name";
          }
          uses MPLS-TE-HEAD-BFD-VIF-INFO;
        }
      }

      container links {
        xr:xr-xml-map "mpls_te_oper:LinkTable";
        description "MPLS TE BFD Info";

        list link {
          xr:xr-xml-map "mpls_te_oper:Link";
          key "interface-name";
          description "MPLS TE BFD Info";
          leaf interface-name {
            xr:xr-xml-map "mpls_te_oper:InterfaceName";
            type xr:Interface-name;
            description "Interface name";
          }
          uses MPLS-LM-BFD-NBRS-LINK-INFO;
        }
      }

      container tail-infos {
        xr:xr-xml-map "mpls_te_oper:P2PTailInfoTable";
        description "MPLS TE Tail BFD Over LSP Table";

        list tail-info {
          xr:xr-xml-map "mpls_te_oper:TailInfo";
          description "MPLS TE Tail End BFD Over LSP Info";
          leaf source-address {
            xr:xr-xml-map "mpls_te_oper:SourceAddress";
            type inet:ipv4-address-no-zone;
            description "Source Address";
          }
          leaf tunnel-id {
            xr:xr-xml-map "mpls_te_oper:TunnelID";
            type int32;
            description "Tunnel ID";
          }
          leaf lsp-id {
            xr:xr-xml-map "mpls_te_oper:LSP_ID";
            type int32;
            description "LSP ID";
          }
          leaf destination-address {
            xr:xr-xml-map "mpls_te_oper:DestinationAddress";
            type inet:ipv4-address-no-zone;
            description "Destination Address";
          }
          leaf extended-tunnel-id {
            xr:xr-xml-map "mpls_te_oper:ExtendedTunnelID";
            type inet:ipv4-address-no-zone;
            description "Extended Tunnel ID";
          }
          leaf ctype {
            xr:xr-xml-map "mpls_te_oper:CType";
            type Ctype;
            description "Ctype";
          }
          leaf p2mp-id {
            xr:xr-xml-map "mpls_te_oper:P2MP_ID";
            type int32;
            description "P2MP ID";
          }
          uses MPLS-TE-TAIL-BFD-LSP-INFO;
        }
      }

      container summary {
        xr:xr-xml-map "mpls_te_oper:Summary";
        description "MPLS TE BFD Summary";
        uses MPLS-TE-BFD-SUMMARY;
      }

      container counters {
        xr:xr-xml-map "mpls_te_oper:Counters";
        description "MPLS TE BFD Counters";
        uses MPLS-TE-BFD-COUNTERS;
      }
    }
  }

  grouping TOPOLOGY-NODE-TABLE {
    description "Common node of mpls-te, mpls-te-standby";

    container topology-nodes {
      xr:xr-xml-map "mpls_te_oper:TopologyNodeTable";
      description "A node in the MPLS-TE topology";

      list topology-node {
        xr:xr-xml-map "mpls_te_oper:TopologyNode";
        key "protocol igp-id area topology-node-type igp-node-id";
        description "A node in the MPLS-TE topology";
        leaf protocol {
          xr:xr-xml-map "mpls_te_oper:Protocol";
          type Mpls-te-igp-protocol;
          description "IGP protocol type";
        }
        leaf igp-id {
          xr:xr-xml-map "mpls_te_oper:IGP_ID";
          type xr:Cisco-ios-xr-string;
          description "IGP instance";
        }
        leaf area {
          xr:xr-xml-map "mpls_te_oper:Area";
          type int32;
          description "IGP area";
        }
        leaf topology-node-type {
          xr:xr-xml-map "mpls_te_oper:TopologyNodeType";
          type Mpls-te-node;
          description "Node type";
        }
        leaf igp-node-id {
          xr:xr-xml-map "mpls_te_oper:IGPNodeID";
          type string;
          description "IGP Node ID";
        }
        uses MPLS-TE-TOPOLOGY-NODE;
      }
    }
  }

  grouping NEIGHBOR-TABLE {
    description "Common node of mpls-lcac, mpls-lcac-standby";

    container neighbors {
      xr:xr-xml-map "mpls_lcac_oper:NeighborTable";
      description "The neighbor information for the local router";

      list neighbor {
        xr:xr-xml-map "mpls_lcac_oper:Neighbor";
        key "interface-name";
        description
          "The neighbors connected to a particular
          interface";
        leaf interface-name {
          xr:xr-xml-map "mpls_lcac_oper:InterfaceName";
          type xr:Interface-name;
          description "Interface name";
        }
        uses MPLS-LM-IGP-NBRS-LINK-INFO;
      }
    }
  }

  grouping GMPLS {
    description "Common node of mpls-lcac, mpls-lcac-standby";

    container gmpls {
      xr:xr-xml-map "mpls_lcac_oper:GMPLS";
      description "GMPLS data";

      container nni {
        xr:xr-xml-map "mpls_lcac_oper:NNI";
        description "GMPLS NNI data";
      }

      container uni {
        xr:xr-xml-map "mpls_lcac_oper:UNI";
        description "GMPLS UNI data";
      }
    }
  }

  grouping ISSU {
    description "Common node of mpls-te, mpls-te-standby";

    container issu {
      xr:xr-xml-map "mpls_te_oper:ISSU";
      description "MPLS TE ISSU information";

      container status {
        xr:xr-xml-map "mpls_te_oper:Status";
        description "MPLS TE ISSU Status information";
        uses TE-NSR-ISSU-STATUS-INFO;
      }

      container detail {
        xr:xr-xml-map "mpls_te_oper:Detail";
        description "MPLS TE ISSU Status information";
        uses TE-NSR-ISSU-STATUS-INFO;
      }
    }
  }

  grouping SOFT-PREEMPTION-GLOBAL-INFO {
    description "Common node of mpls-lcac, mpls-lcac-standby";

    container soft-preemption-global-info {
      xr:xr-xml-map "mpls_lcac_oper:SoftPreemptionGlobalInfo";
      description "The global soft-preemption information";
      uses MPLS-TE-SOFT-PREEMPTION-GLOBAL-INFO;
    }
  }

  container mpls-te {
    xr:xr-xml-map "mpls_te_oper:MPLS_TE";
    config false;
    description "MPLS Traffic Engineering operational data";

    container segment-routing {
      xr:xr-xml-map "mpls_te_oper:SegmentRouting";
      description "The Segment Routing database in MPLS-TE";

      container srigp-area-infos {
        xr:xr-xml-map "mpls_te_oper:SRAreaTable";
        description "Segment-Routing information about IGP areas";

        list srigp-area-info {
          xr:xr-xml-map "mpls_te_oper:SRIGPAreaInfo";
          key "protocol igp-instance area";
          description "A Segment-Routing IGP area information";
          leaf protocol {
            xr:xr-xml-map "mpls_te_oper:Protocol";
            type Mpls-te-igp-protocol;
            description "IGP protocol type";
          }
          leaf igp-instance {
            xr:xr-xml-map "mpls_te_oper:IGP_Instance";
            type xr:Cisco-ios-xr-string;
            description "IGP instance";
          }
          leaf area {
            xr:xr-xml-map "mpls_te_oper:Area";
            type int32;
            description "IGP area";
          }
          uses TE-SR-IGP-AREA;
        }
      }

      container sr-node-infos {
        xr:xr-xml-map "mpls_te_oper:SRNodeTable";
        description "Segment-Routing nodes database in MPLS-TE";

        list sr-node-info {
          xr:xr-xml-map "mpls_te_oper:SRNodeInfo";
          key "protocol igp-instance area igp-node-id";
          description "A Segment-Routing node information";
          leaf protocol {
            xr:xr-xml-map "mpls_te_oper:Protocol";
            type Mpls-te-igp-protocol;
            description "IGP protocol type";
          }
          leaf igp-instance {
            xr:xr-xml-map "mpls_te_oper:IGP_Instance";
            type xr:Cisco-ios-xr-string;
            description "IGP instance";
          }
          leaf area {
            xr:xr-xml-map "mpls_te_oper:Area";
            type int32;
            description "IGP area";
          }
          leaf igp-node-id {
            xr:xr-xml-map "mpls_te_oper:IGPNodeID";
            type string;
            description "Node's IGP ID";
          }
          uses TE-SR-NODE;
        }
      }

      container sr-prefix-infos {
        xr:xr-xml-map "mpls_te_oper:SRPrefixTable";
        description "Segment-Routing prefixes database in MPLS-TE";

        list sr-prefix-info {
          xr:xr-xml-map "mpls_te_oper:SRPrefixInfo";
          key "protocol igp-instance area prefix prefix-length";
          description "A Segment-Routing prefix information";
          leaf protocol {
            xr:xr-xml-map "mpls_te_oper:Protocol";
            type Mpls-te-igp-protocol;
            description "IGP protocol type";
          }
          leaf igp-instance {
            xr:xr-xml-map "mpls_te_oper:IGP_Instance";
            type xr:Cisco-ios-xr-string;
            description "IGP instance";
          }
          leaf area {
            xr:xr-xml-map "mpls_te_oper:Area";
            type int32;
            description "IGP area";
          }
          leaf prefix {
            xr:xr-xml-map "mpls_te_oper:Prefix";
            type inet:ipv4-address-no-zone;
            description "Segment-Routing prefix";
          }
          leaf prefix-length {
            xr:xr-xml-map "mpls_te_oper:Prefix_Length";
            type int32;
            description "Prefix' length";
          }
          uses TE-SR-PREFIX;
        }
      }
    }

    container fib-next-hop-routes {
      xr:xr-xml-map "mpls_te_oper:FIBNextHopRouteTable";
      description "MPLS TE FIB nexthop route database";

      list fib-next-hop-route {
        xr:xr-xml-map "mpls_te_oper:FIBNextHopRoute";
        key "prefix-address";
        description "MPLS TE FIB nexthop route";
        leaf prefix-address {
          xr:xr-xml-map "mpls_te_oper:PrefixAddress";
          type inet:ipv4-address-no-zone;
          description "Prefix Address";
        }
        uses TE-FIB-NH-ROUTE-BAG;
      }
    }

    container next-hop-routes {
      xr:xr-xml-map "mpls_te_oper:NextHopRouteTable";
      description "MPLS TE nexthop route database";

      list next-hop-route {
        xr:xr-xml-map "mpls_te_oper:NextHopRoute";
        description "MPLS TE nexthop route";
        leaf prefix-address {
          xr:xr-xml-map "mpls_te_oper:PrefixAddress";
          type inet:ipv4-address-no-zone;
          description "Prefix Address";
        }
        leaf prefix-length {
          xr:xr-xml-map "mpls_te_oper:PrefixLength";
          type xr:Ipv4-prefix-length;
          description "Prefix Length";
        }
        leaf next-hop-type {
          xr:xr-xml-map "mpls_te_oper:NextHopType";
          type Mpls-te-next-hop;
          description "Next-hop Route Type";
        }
        uses TE-NEXTHOP-ROUTE;
      }
    }

    container auto-route-destination-entries {
      xr:xr-xml-map "mpls_te_oper:AutorouteDestinationTunnelTable";
      description
        "MPLS TE autoroute destination table indexed by
        tunnel";

      list auto-route-destination-entry {
        xr:xr-xml-map "mpls_te_oper:AutoRouteDestinationEntry";
        key "tunnel-id";
        description
          "MPLS TE autoroute destination info for one
          tunnel";
        leaf tunnel-id {
          xr:xr-xml-map "mpls_te_oper:TunnelID";
          type int32;
          description "Tunnel ID";
        }
        uses TE-TUNNEL-AUTOROUTE-DESTINATIONS;
      }
    }

    container te-mib {
      xr:xr-xml-map "mpls_te_oper:TE_MIB";
      description "TE MIB information";

      container scalars {
        xr:xr-xml-map "mpls_te_oper:Scalars";
        description "MIB Scalar information";
        uses MPLS-TE-MIB-SCALAR-INFO;
      }
    }
    uses P2P-P2MP-TUNNEL;
    uses TOPOLOGY-NODE-TABLE;
    uses ANNOUNCE-TUNNELS-INFO;
    uses COLLABORATOR-TIMERS;
    uses AUTO-TUNNEL;
    uses SOFT-PREEMPTION;
    uses FORWARDING-ADJACENCY-DESTINATION-TABLE;
    uses IGP-AREA-TABLE;
    uses WRAP-PROTECTION;
    uses TOPOLOGY;
    uses SIGNALLING-COUNTERS;
    uses DIFF-SERV-TE-CLASSES;
    uses ISSU;
    uses FAST-REROUTE;
    uses ATTRIBUTE-SET-TABLE;
    uses IGP-AREA-BRIEF-TABLE;
    uses TUNNELS;
    uses MAXIMUM-TUNNELS;
    uses PATH-PROTECTION;
    uses P2MP;
    uses OPEN-CONFIG;
    uses BFD;
    uses NSR;
    uses AFFINITY-MAP;
    uses TOPOLOGY-BRIEF-TABLE;
  }

  container mpls-lcac-standby {
    xr:xr-xml-map "mpls_lcac_oper:MPLS_LCACStandby";
    config false;
    description "mpls lcac standby";
    uses NEIGHBOR-TABLE;
    uses PREEMPTION-EVENT-TABLE;
    uses ADVERTISEMENTS;
    uses STATISTICS;
    uses BANDWIDTH-ALLOCATION;
    uses GMPLS;
    uses BFD-NEIGHBOR-TABLE;
    uses LINK-SUMMARY;
    uses LINK-INFORMATION;
    uses ADMISSION-CONTROL;
    uses SOFT-PREEMPTION-GLOBAL-INFO;
    uses SOFT-PREEMPTION-TABLE;
  }

  container mpls-lcac {
    xr:xr-xml-map "mpls_lcac_oper:MPLS_LCAC";
    config false;
    description "mpls lcac";
    uses NEIGHBOR-TABLE;
    uses PREEMPTION-EVENT-TABLE;
    uses ADVERTISEMENTS;
    uses STATISTICS;
    uses BANDWIDTH-ALLOCATION;
    uses GMPLS;
    uses BFD-NEIGHBOR-TABLE;
    uses LINK-SUMMARY;
    uses LINK-INFORMATION;
    uses ADMISSION-CONTROL;
    uses SOFT-PREEMPTION-GLOBAL-INFO;
    uses SOFT-PREEMPTION-TABLE;
  }

  container mpls-pce {
    xr:xr-xml-map "te_pce_oper:MPLS_PCE";
    config false;
    description "mpls pce";
    uses LSP-TABLE;
    uses TE-PCE-OPER-STATISTICS;
    uses PEER-TABLE;
    uses TE-PCE-OPER-TOPOLOGY;
    uses TUNNEL-TABLE;
  }

  container mpls-pce-stdby {
    xr:xr-xml-map "te_pce_oper:MPLS_PCE_STDBY";
    config false;
    description "mpls pce stdby";
    uses LSP-TABLE;
    uses TE-PCE-OPER-STATISTICS;
    uses PEER-TABLE;
    uses TE-PCE-OPER-TOPOLOGY;
    uses TUNNEL-TABLE;
  }

  container mpls-tp {
    xr:xr-xml-map "mpls_te_oper:MPLS_TP";
    config false;
    description "mpls tp";

    container tp-links {
      xr:xr-xml-map "mpls_te_oper:TPLinks";
      description "Transport profile links";

      container tp-detail-links {
        xr:xr-xml-map "mpls_te_oper:TPDetailLinkTable";
        description "Detailed table of transport profile links";

        list tp-detail-link {
          xr:xr-xml-map "mpls_te_oper:TPDetailLink";
          key "tp-link-id";
          description
            "Detailed information of transport profile link";
          leaf tp-link-id {
            xr:xr-xml-map "mpls_te_oper:TPLinkID";
            type int32;
            description "Numeric transport profile link identifier";
          }
          uses MPLS-TE-TP-DETAIL-LINK-INFO;
        }
      }

      container tp-link-summary {
        xr:xr-xml-map "mpls_te_oper:TPLinkSummary";
        description "Summary of transport profile links";
        uses MPLS-TE-TP-LINK-SUMMARY-INFO;
      }

      container tp-links {
        xr:xr-xml-map "mpls_te_oper:TPLinkTable";
        description "Table of transport profile links";

        list tp-link {
          xr:xr-xml-map "mpls_te_oper:TPLink";
          key "tp-link-id";
          description "Brief information of transport profile link";
          leaf tp-link-id {
            xr:xr-xml-map "mpls_te_oper:TPLinkID";
            type int32;
            description "Numeric transport profile link identifier";
          }
          uses MPLS-TE-TP-LINK-INFO;
        }
      }
    }

    container tp-tunnels {
      xr:xr-xml-map "mpls_te_oper:TPTunnels";
      description "Transport profile tunnels";

      container tp-tunnel-summary {
        xr:xr-xml-map "mpls_te_oper:TPTunnelSummary";
        description "Summary of transport profile tunnels";
        uses MPLS-TE-TP-TUNNEL-SUMMARY;
      }

      container tp-detail-tunnels {
        xr:xr-xml-map "mpls_te_oper:TPDetailTunnelTable";
        description "Detailed table of transport profile tunnels";

        list tp-detail-tunnel {
          xr:xr-xml-map "mpls_te_oper:TPDetailTunnel";
          key "tp-tunnel-name";
          description
            "Detailed information of transport profile
            tunnel";
          leaf tp-tunnel-name {
            xr:xr-xml-map "mpls_te_oper:TPTunnelName";
            type xr:Cisco-ios-xr-string;
            description "Tunnel name";
          }
          uses MPLS-TE-TP-DETAIL-TUNNEL-INFO;
        }
      }

      container tp-tunnels {
        xr:xr-xml-map "mpls_te_oper:TPTunnelTable";
        description "Table of transport profile tunnels";

        list tp-tunnel {
          xr:xr-xml-map "mpls_te_oper:TPTunnel";
          key "tp-tunnel-name";
          description
            "Brief information of transport profile tunnel";
          leaf tp-tunnel-name {
            xr:xr-xml-map "mpls_te_oper:TPTunnelName";
            type xr:Cisco-ios-xr-string;
            description "Tunnel name";
          }
          uses MPLS-TE-TP-TUNNEL-INFO;
        }
      }
    }

    container tp-midpoints {
      xr:xr-xml-map "mpls_te_oper:TPMidpoints";
      description "Transport profile mid-point";

      container tp-detail-midpoints {
        xr:xr-xml-map "mpls_te_oper:TPDetailMidpointTable";
        description
          "Detailed table of transport profile mid-points";

        list tp-detail-midpoint {
          xr:xr-xml-map "mpls_te_oper:TPDetailMidpoint";
          key "tp-midpoint-name";
          description
            "Detailed information of transport profile
            mid-point";
          leaf tp-midpoint-name {
            xr:xr-xml-map "mpls_te_oper:TPMidpointName";
            type xr:Cisco-ios-xr-string;
            description "Mid-point name";
          }
          uses MPLS-TP-DETAIL-MID-INFO;
        }
      }

      container tp-midpoint-summary {
        xr:xr-xml-map "mpls_te_oper:TPMidpointSummary";
        description "Summary of transport profile mid-points";
        uses MPLS-TP-MID-SUMMARY-INFO;
      }

      container tp-midpoints {
        xr:xr-xml-map "mpls_te_oper:TPMidpointTable";
        description "Table of transport profile mid-points";

        list tp-midpoint {
          xr:xr-xml-map "mpls_te_oper:TPMidpoint";
          key "tp-midpoint-name";
          description
            "Brief information of transport profile
            mid-point";
          leaf tp-midpoint-name {
            xr:xr-xml-map "mpls_te_oper:TPMidpointName";
            type xr:Cisco-ios-xr-string;
            description "Mid-point name";
          }
          uses MPLS-TP-MID-INFO;
        }
      }
    }

    container tp-global-parameters {
      xr:xr-xml-map "mpls_te_oper:TPGlobalParameters";
      description "Transport profile global parameters";
      uses MPLS-TE-TP-GLOBAL-INFO;
    }
  }

  container mpls-te-standby {
    xr:xr-xml-map "mpls_te_oper:MPLS_TEStandby";
    config false;
    description "mpls te standby";
    uses P2P-P2MP-TUNNEL;
    uses TOPOLOGY-NODE-TABLE;
    uses ANNOUNCE-TUNNELS-INFO;
    uses COLLABORATOR-TIMERS;
    uses AUTO-TUNNEL;
    uses SOFT-PREEMPTION;
    uses FORWARDING-ADJACENCY-DESTINATION-TABLE;
    uses IGP-AREA-TABLE;
    uses WRAP-PROTECTION;
    uses TOPOLOGY;
    uses SIGNALLING-COUNTERS;
    uses DIFF-SERV-TE-CLASSES;
    uses ISSU;
    uses FAST-REROUTE;
    uses ATTRIBUTE-SET-TABLE;
    uses IGP-AREA-BRIEF-TABLE;
    uses TUNNELS;
    uses MAXIMUM-TUNNELS;
    uses PATH-PROTECTION;
    uses P2MP;
    uses OPEN-CONFIG;
    uses BFD;
    uses NSR;
    uses AFFINITY-MAP;
    uses TOPOLOGY-BRIEF-TABLE;
  }
}
