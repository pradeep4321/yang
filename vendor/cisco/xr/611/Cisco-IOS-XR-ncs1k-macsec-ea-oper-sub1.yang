submodule Cisco-IOS-XR-ncs1k-macsec-ea-oper-sub1 {

  belongs-to Cisco-IOS-XR-ncs1k-macsec-ea-oper {
    prefix Cisco-IOS-XR-ncs1k-macsec-ea-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ncs1k-macsec-ea package operational data.

     Copyright (c) 2013-2016 by Cisco Systems, Inc.
     All rights reserved.";

  revision "2015-11-09" {
    description
      "IOS XR 6.0 revision.";
  }

  typedef Ncs1k-cipher-suit {
    type enumeration {
      enum gcm-aes-256 {
        value 0;
        description "GCM AES 256";
      }
      enum gcm-aes-128 {
        value 1;
        description "GCM AES 128";
      }
      enum gcm-aes-xpn-256 {
        value 2;
        description "GCM AES XPN 256";
      }
    }
    description "Ncs1k cipher suit";
  }

  grouping NCS1K-AN-STATUS {
    description "Association Number status";
    leaf association-number {
      xr:xr-xml-map "ncs1k_macsec_ea_show:AssociationNumber";
      type uint8;
      description "Assocition Number";
    }
    leaf device-association-number {
      xr:xr-xml-map "ncs1k_macsec_ea_show:DeviceAssociationNumber";
      type uint8;
      description "Devive Association Number";
    }
    leaf short-secure-channel-id {
      xr:xr-xml-map "ncs1k_macsec_ea_show:ShortSecureChannelId";
      type uint32;
      description "Short Secure Channel Id";
    }
    leaf programmed-time {
      xr:xr-xml-map "ncs1k_macsec_ea_show:ProgrammedTime";
      type string;
      description "Key Programmed Time";
    }
    leaf key-crc {
      xr:xr-xml-map "ncs1k_macsec_ea_show:KeyCRC";
      type uint32;
      description "32bit CRC of Programmed Key";
    }
    leaf-list xpn-salt {
      xr:xr-xml-map "ncs1k_macsec_ea_show:XpnSalt";
      type uint32;
      description "XPN Salt";
    }
  }

  grouping NCS1K-SC-STATUS {
    description "Secure Channel status";
    leaf protection-enabled {
      xr:xr-xml-map "ncs1k_macsec_ea_show:ProtectionEnabled";
      type boolean;
      description "Protection Enabled";
    }
    leaf secure-channel-id {
      xr:xr-xml-map "ncs1k_macsec_ea_show:SecureChannelId";
      type uint64;
      description "Secure Channel Id";
    }
    leaf confidentiality-offset {
      xr:xr-xml-map "ncs1k_macsec_ea_show:ConfidentialityOffset";
      type uint32;
      description "Confidentiality offset";
    }
    leaf cipher-suite {
      xr:xr-xml-map "ncs1k_macsec_ea_show:CipherSuite";
      type Ncs1k-cipher-suit;
      description "Cipher Suite";
    }
    leaf initial-packet-number {
      xr:xr-xml-map "ncs1k_macsec_ea_show:InitialPacketNumber";
      type uint64;
      description "Initial Packet Number";
    }
    leaf secure-tag-length {
      xr:xr-xml-map "ncs1k_macsec_ea_show:SecureTagLength";
      type uint32;
      description "Secure Tag Length";
    }
    leaf max-packet-number {
      xr:xr-xml-map "ncs1k_macsec_ea_show:MaxPacketNumber";
      type uint64;
      description "Maximum Packet Number";
    }
    leaf recent-packet-number {
      xr:xr-xml-map "ncs1k_macsec_ea_show:RecentPacketNumber";
      type uint64;
      description "Recent Packet Number";
    }

    list active-association {
      description "Active Associations";
      uses NCS1K-AN-STATUS;
    }
  }

  grouping NCS1K-MACSEC-IF-STATUS {
    description "Interface Status details";

    container encrypt-sc-status {
      description "Encrypt Secure Channel Status";
      uses NCS1K-SC-STATUS;
    }

    container decrypt-sc-status {
      description "Decrypt Secure Channel Status";
      uses NCS1K-SC-STATUS;
    }
    leaf replay-window-size {
      xr:xr-xml-map "ncs1k_macsec_ea_show:ReplayWindowSize";
      type uint32;
      description "Replay Window Size";
    }
    leaf must-secure {
      xr:xr-xml-map "ncs1k_macsec_ea_show:MustSecure";
      type boolean;
      description "Must Secure";
    }
  }
}
