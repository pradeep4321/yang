submodule Cisco-IOS-XR-ncs1k-mxp-oper-sub1 {

  belongs-to Cisco-IOS-XR-ncs1k-mxp-oper {
    prefix Cisco-IOS-XR-ncs1k-mxp-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ncs1k-mxp package operational data.

     Copyright (c) 2013-2016 by Cisco Systems, Inc.
     All rights reserved.";

  revision "2015-11-09" {
    description
      "IOS XR 6.0 revision.";
  }

  typedef Hw-module-slice-status {
    type enumeration {
      enum not-provisioned {
        value 0;
        description "Not Provisioned";
      }
      enum provisioning-in-progress {
        value 1;
        description "Provisioning In-Progress";
      }
      enum provisioned {
        value 2;
        description "Provisioned";
      }
      enum provisioning-failed {
        value 3;
        description "Provisioning Failed";
      }
      enum provisioning-scheduled {
        value 4;
        description "Provisioning Scheduled";
      }
      enum reprovisioning-aborted {
        value 5;
        description "Reprovisioning Aborted";
      }
    }
    description "Hw module slice status";
  }

  grouping HW-MODULE-SLICE-CLIENT-TRAFFIC-SPLIT-INFO-B {
    description "HW MODULE SLICE CLIENT TRAFFIC SPLIT INFO B";
    leaf trunk-name {
      xr:xr-xml-map "mxp_show_hwmod:TrunkName";
      type string {
        length "0..64";
      }
      description "TrunkName";
    }
    leaf if-index {
      xr:xr-xml-map "mxp_show_hwmod:IfIndex";
      type uint32;
      description "IfIndex";
    }
    leaf percentage {
      xr:xr-xml-map "mxp_show_hwmod:Percentage";
      type string {
        length "0..8";
      }
      description "Percentage";
    }
  }

  grouping HW-MODULE-SLICE-CLIENT-PORT-INFO-B {
    description "HW MODULE SLICE CLIENT PORT INFO B";
    leaf client-name {
      xr:xr-xml-map "mxp_show_hwmod:ClientName";
      type string {
        length "0..64";
      }
      description "ClientName";
    }
    leaf if-index {
      xr:xr-xml-map "mxp_show_hwmod:IfIndex";
      type uint32;
      description "IfIndex";
    }

    list trunk-port {
      description "trunk port";
      uses HW-MODULE-SLICE-CLIENT-TRAFFIC-SPLIT-INFO-B;
    }
  }

  grouping HW-MODULE-SLICE-INFO-B {
    description "HW MODULE SLICE INFO B";
    leaf slice-id {
      xr:xr-xml-map "mxp_show_hwmod:SliceId";
      type uint32;
      description "SliceId";
    }
    leaf client-rate {
      xr:xr-xml-map "mxp_show_hwmod:ClientRate";
      type uint32;
      description "ClientRate";
    }
    leaf trunk-rate {
      xr:xr-xml-map "mxp_show_hwmod:TrunkRate";
      type uint32;
      description "TrunkRate";
    }
    leaf hardware-status {
      xr:xr-xml-map "mxp_show_hwmod:HardwareStatus";
      type Hw-module-slice-status;
      description "HardwareStatus";
    }
    leaf dp-fpg-ver {
      xr:xr-xml-map "mxp_show_hwmod:DpFpgVer";
      type string {
        length "0..16";
      }
      description "DpFpgVer";
    }
    leaf need-upg {
      xr:xr-xml-map "mxp_show_hwmod:NeedUpg";
      type uint32;
      description "NeedUpg";
    }
    leaf encryption-supported {
      xr:xr-xml-map "mxp_show_hwmod:EncryptionSupported";
      type boolean;
      description "EncryptionSupported";
    }

    list client-port {
      description "client port";
      uses HW-MODULE-SLICE-CLIENT-PORT-INFO-B;
    }
  }

  grouping MXP-HWMOD-OP {
    description "ipsec cli o/p entry";

    list slice-info {
      description "slice info";
      uses HW-MODULE-SLICE-INFO-B;
    }
  }
}
