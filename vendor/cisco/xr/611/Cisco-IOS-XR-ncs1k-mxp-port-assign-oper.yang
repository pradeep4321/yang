module Cisco-IOS-XR-ncs1k-mxp-port-assign-oper {

  /*** NAMESPACE / PREFIX DEFINITION ***/

  namespace "http://cisco.com/ns/yang"+
    "/Cisco-IOS-XR-ncs1k-mxp-port-assign-oper";


  prefix "ncs1k-mxp-port-assign-oper";

  /*** LINKAGE (IMPORTS / INCLUDES) ***/

  import Cisco-IOS-XR-types { prefix "xr"; }

  include Cisco-IOS-XR-ncs1k-mxp-port-assign-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ncs1k-mxp-port-assign package operational data.

     This module contains definitions
     for the following management objects:
       optical-interface: System-wide view of interface operational
         data

     Copyright (c) 2013-2016 by Cisco Systems, Inc.
     All rights reserved.";

  revision "2015-11-09" {
    description
      "IOS XR 6.0 revision.";
  }


  container optical-interface {
    xr:xr-xml-map "mxp_port_assign_oper:OpticalInterface";
    config false;
    description "System-wide view of interface operational data";

    container optical-client-interfaces {
      xr:xr-xml-map "mxp_port_assign_oper:OpticalClientInterfaceTab"+
        "le";
      description
        "The operational attributes table for Client Port";

      list optical-client-interface {
        xr:xr-xml-map "mxp_port_assign_oper:OpticalClientInterface";
        key "name";
        description "The operational attributes for Client Port";

        container optical-client-logical-channel-assignments {
          xr:xr-xml-map "mxp_port_assign_oper:OpticalClientLogicalC"+
            "hannelAssignmentTable";
          description
            "The operational attributes for a Underline
            Ether Interface";

          list optical-client-logical-channel-assignment {
            xr:xr-xml-map "mxp_port_assign_oper:OpticalClientLogica"+
              "lChannelAssignment";
            key "index";
            description
              "The operational attributes for a Underline
              Ether Interface";
            leaf index {
              xr:xr-xml-map "mxp_port_assign_oper:Index";
              type int32;
              description "The index of the interface";
            }
            uses LOGICAL-CHAN-ASSIGNMENT;
          }
        }
        leaf name {
          xr:xr-xml-map "mxp_port_assign_oper:Name";
          type xr:Interface-name;
          description "The name of the client interface";
        }
      }
    }

    container optical-logical-interfaces {
      xr:xr-xml-map "mxp_port_assign_oper:OpticalLogicalInterfaceTa"+
        "ble";
      description
        "The operational attributes for a particular
        interface";

      list optical-logical-interface {
        xr:xr-xml-map "mxp_port_assign_oper:OpticalLogicalInterface";
        key "index";
        description
          "The operational attributes for a particular
          interface";

        container optical-logical-interface-attr {
          xr:xr-xml-map "mxp_port_assign_oper:OpticalLogicalInterfa"+
            "ceAttr";
          description
            "The operational attributes for a particular
            interface";
          uses LOGICAL-CHANNEL-ATTR;
        }

        container "optical-logical-interface-logical-channel"+
          "-assignments" {
          xr:xr-xml-map "mxp_port_assign_oper:OpticalLogicalInterfa"+
            "ceLogicalChannel";
          description
            "The operational attributes for a particular
            interface";

          list "optical-logical-interface-logical-channel"+
            "-assignment" {
            xr:xr-xml-map "mxp_port_assign_oper:OpticalLogicalInter"+
              "faceLogicalChannelAssignment";
            key "index";
            description
              "The operational attributes for a particular
              interface";
            leaf index {
              xr:xr-xml-map "mxp_port_assign_oper:Index";
              type int32;
              description "The index of the interface";
            }
            uses LOGICAL-CHAN-ASSIGNMENT;
          }
        }
        leaf index {
          xr:xr-xml-map "mxp_port_assign_oper:Index";
          type int32;
          description "The index of the logical-channel";
        }
      }
    }
  }
}
