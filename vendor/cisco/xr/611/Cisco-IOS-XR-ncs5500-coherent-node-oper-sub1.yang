submodule Cisco-IOS-XR-ncs5500-coherent-node-oper-sub1 {

  belongs-to Cisco-IOS-XR-ncs5500-coherent-node-oper {
    prefix Cisco-IOS-XR-ncs5500-coherent-node-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ncs5500-coherent-node package operational data.

     Copyright (c) 2013-2016 by Cisco Systems, Inc.
     All rights reserved.";

  revision "2015-11-09" {
    description
      "IOS XR 6.0 revision.";
  }


  grouping PORTMODE-INFO {
    description "portmode entry of optics controller";
    leaf intf-name {
      xr:xr-xml-map "coherent:INTF_NAME";
      type string;
      description "Interface Name";
    }
    leaf speed {
      xr:xr-xml-map "coherent:SPEED";
      type string;
      description "Optics speed";
    }
    leaf fec {
      xr:xr-xml-map "coherent:FEC";
      type string;
      description "Optics fec";
    }
    leaf diff {
      xr:xr-xml-map "coherent:DIFF";
      type string;
      description "Optics diff";
    }
    leaf modulation {
      xr:xr-xml-map "coherent:MODULATION";
      type string;
      description "Optics modulation";
    }
  }

  grouping COH-PORTMODE-ALL-DETAILS {
    description "Optics controllers port Information";
    leaf num-entries {
      xr:xr-xml-map "coherent:num_entries";
      type uint32;
      description "Number of dev map entries";
    }

    list portmode-entry {
      max-elements "32";
      description "portmode entry";
      uses PORTMODE-INFO;
    }
  }

  grouping COH-ETH-INTERFACE-DATA {
    description "Hundredgig interface data";
    leaf ifname {
      xr:xr-xml-map "coherent:ifname";
      type string {
        length "0..64";
      }
      description "ifname";
    }
    leaf intf-handle {
      xr:xr-xml-map "coherent:intf_handle";
      type uint32;
      description "intf handle";
    }
    leaf admin-state {
      xr:xr-xml-map "coherent:admin_state";
      type boolean;
      description "admin state";
    }
  }

  grouping COH-ETH-INTERFACE-INFO {
    description "Hundredgig interface info";
    leaf intf-count {
      xr:xr-xml-map "coherent:intf_count";
      type int32;
      description "intf count";
    }

    list eth-data {
      max-elements "2";
      description "eth data";
      uses COH-ETH-INTERFACE-DATA;
    }
  }

  grouping COH-PLUGGABLE-INFO {
    description "Coherent pluggable information";
    leaf deviation {
      xr:xr-xml-map "coherent:deviation";
      type string {
        length "0..16";
      }
      description "deviation";
    }
    leaf part-number {
      xr:xr-xml-map "coherent:part_number";
      type string {
        length "0..16";
      }
      description "part number";
    }
    leaf serial-number {
      xr:xr-xml-map "coherent:serial_number";
      type string {
        length "0..16";
      }
      description "serial number";
    }
    leaf date-code-number {
      xr:xr-xml-map "coherent:date_code_number";
      type string {
        length "0..10";
      }
      description "date code number";
    }
    leaf clei-code-number {
      xr:xr-xml-map "coherent:CLEI_code_number";
      type string {
        length "0..10";
      }
      description "CLEI code number";
    }
    leaf module-hardware-version-number {
      xr:xr-xml-map "coherent:module_hardware_version_number";
      type uint16;
      description "module hardware version number";
    }
    leaf module-firmware-running-version-number {
      xr:xr-xml-map "coherent:module_firmware_running_version_numbe"+
        "r";
      type uint16;
      description "module firmware running version number";
    }
    leaf module-firmware-committed-version-number {
      xr:xr-xml-map "coherent:module_firmware_committed_version_num"+
        "ber";
      type uint16;
      description "module firmware committed version number";
    }
    leaf vendorname {
      xr:xr-xml-map "coherent:vendorname";
      type string {
        length "0..16";
      }
      description "vendorname";
    }
    leaf description {
      xr:xr-xml-map "coherent:description";
      type string {
        length "0..64";
      }
      description "description";
    }
    leaf pid {
      xr:xr-xml-map "coherent:pid";
      type string {
        length "0..16";
      }
      description "pid";
    }
    leaf vid {
      xr:xr-xml-map "coherent:vid";
      type string {
        length "0..16";
      }
      description "vid";
    }
    leaf ctp-type {
      xr:xr-xml-map "coherent:ctp_type";
      type uint32;
      description "ctp type";
    }
  }

  grouping COH-PORT-DATA {
    description "Coherent front panel port data";

    container ctp-info {
      description "ctp info";
      uses COH-PLUGGABLE-INFO;
    }

    container interface-info {
      description "interface info";
      uses COH-ETH-INTERFACE-INFO;
    }
    leaf optics-ctrl-created {
      xr:xr-xml-map "coherent:optics_ctrl_created";
      type boolean;
      description "optics ctrl created";
    }
    leaf dsp-ctrl-created {
      xr:xr-xml-map "coherent:dsp_ctrl_created";
      type boolean;
      description "dsp ctrl created";
    }
    leaf has-pluggable {
      xr:xr-xml-map "coherent:has_pluggable";
      type boolean;
      description "has pluggable";
    }
    leaf optics-admin-up {
      xr:xr-xml-map "coherent:optics_admin_up";
      type boolean;
      description "optics admin up";
    }
    leaf dsp-admin-up {
      xr:xr-xml-map "coherent:dsp_admin_up";
      type boolean;
      description "dsp admin up";
    }
    leaf laser-state {
      xr:xr-xml-map "coherent:laser_state";
      type boolean;
      description "laser state";
    }
    leaf fp-port-idx {
      xr:xr-xml-map "coherent:fp_port_idx";
      type uint32;
      description "fp port idx";
    }
    leaf wavelength {
      xr:xr-xml-map "coherent:wavelength";
      type uint32;
      description "wavelength";
    }
    leaf traffic-type {
      xr:xr-xml-map "coherent:traffic_type";
      type uint32;
      description "traffic type";
    }
    leaf laser-op-rc {
      xr:xr-xml-map "coherent:laser_op_rc";
      type int32;
      description "laser op rc";
    }
    leaf wlen-op-rc {
      xr:xr-xml-map "coherent:wlen_op_rc";
      type int32;
      description "wlen op rc";
    }
    leaf traffic-op-rc {
      xr:xr-xml-map "coherent:traffic_op_rc";
      type int32;
      description "traffic op rc";
    }
  }

  grouping COH-HEALTH-DATA {
    description "Coherent health Data";
    leaf im-state {
      xr:xr-xml-map "coherent:im_state";
      type boolean;
      description "im state";
    }
    leaf aipc-srvr-state {
      xr:xr-xml-map "coherent:aipc_srvr_state";
      type boolean;
      description "aipc srvr state";
    }
    leaf sysdb-state {
      xr:xr-xml-map "coherent:sysdb_state";
      type boolean;
      description "sysdb state";
    }
    leaf pm-state {
      xr:xr-xml-map "coherent:pm_state";
      type boolean;
      description "pm state";
    }
    leaf optics-ea-conn {
      xr:xr-xml-map "coherent:optics_ea_conn";
      type boolean;
      description "optics ea conn";
    }
    leaf dsp-ea-conn {
      xr:xr-xml-map "coherent:dsp_ea_conn";
      type boolean;
      description "dsp ea conn";
    }
    leaf vether-state {
      xr:xr-xml-map "coherent:vether_state";
      type boolean;
      description "vether state";
    }
    leaf morgoth-alive {
      xr:xr-xml-map "coherent:morgoth_alive";
      type boolean;
      description "morgoth alive";
    }
    leaf prov-infra-state {
      xr:xr-xml-map "coherent:prov_infra_state";
      type boolean;
      description "prov infra state";
    }
    leaf sdk-fpga-compatible {
      xr:xr-xml-map "coherent:sdk_fpga_compatible";
      type boolean;
      description "sdk fpga compatible";
    }
    leaf morgoth-version {
      xr:xr-xml-map "coherent:morgoth_version";
      type string {
        length "0..255";
      }
      description "morgoth version";
    }
    leaf sdk-version {
      xr:xr-xml-map "coherent:sdk_version";
      type string {
        length "0..255";
      }
      description "sdk version";
    }
    leaf denali-version {
      xr:xr-xml-map "coherent:denali_version";
      type string {
        length "0..255";
      }
      description "denali version";
    }
    leaf board-type {
      xr:xr-xml-map "coherent:board_type";
      type string {
        length "0..255";
      }
      description "board type";
    }
    leaf jlink-op {
      xr:xr-xml-map "coherent:jlink_op";
      type string {
        length "0..1024";
      }
      description "jlink op";
    }

    list port-data {
      max-elements "6";
      description "port data";
      uses COH-PORT-DATA;
    }
  }

  grouping COH-DEV-MAP-ENTRY {
    description "coherent device mapping entry";
    leaf device-address {
      xr:xr-xml-map "coherent:device_address";
      type uint32;
      description "Device address";
    }
    leaf ifhandle {
      xr:xr-xml-map "coherent:ifhandle";
      type uint32;
      description "Interface handle";
    }
    leaf intf-name {
      xr:xr-xml-map "coherent:INTF_NAME";
      type string;
      description "Interface Name";
    }
  }

  grouping COH-DEV-MAP-DATA {
    description "Coherent device mapping Information";
    leaf num-entries {
      xr:xr-xml-map "coherent:num_entries";
      type uint32;
      description "Number of dev map entries";
    }

    list dev-map {
      max-elements "32";
      description "dev map";
      uses COH-DEV-MAP-ENTRY;
    }
  }
}
