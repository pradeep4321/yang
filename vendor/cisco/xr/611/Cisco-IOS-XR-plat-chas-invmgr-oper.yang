module Cisco-IOS-XR-plat-chas-invmgr-oper {

  /*** NAMESPACE / PREFIX DEFINITION ***/

  namespace "http://cisco.com/ns/yang"+
    "/Cisco-IOS-XR-plat-chas-invmgr-oper";


  prefix "plat-chas-invmgr-oper";

  /*** LINKAGE (IMPORTS / INCLUDES) ***/

  import Cisco-IOS-XR-types { prefix "xr"; }

  include Cisco-IOS-XR-plat-chas-invmgr-oper-sub2 {
    revision-date 2015-01-07;
  }

  include Cisco-IOS-XR-plat-chas-invmgr-oper-sub1 {
    revision-date 2015-01-07;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR plat-chas-invmgr package operational data.

     This module contains definitions
     for the following management objects:
       platform: Platform information
       platform-inventory: platform inventory

     Copyright (c) 2013-2016 by Cisco Systems, Inc.
     All rights reserved.";

  revision "2015-01-07" {
    description
      "IOS XR 5.3.1 revision.";
  }


  grouping STATE {
    description "Common node of instance, slot";

    container state {
      xr:xr-xml-map "platform_common:State";
      description "State information";
      uses PLATFORM-INFO;
    }
  }

  grouping PORT-SLOT-TABLE {
    description "Common node of card, module";

    container port-slots {
      xr:xr-xml-map "inventory_common:PortSlotTable";
      description "Table of port slots";

      list port-slot {
        xr:xr-xml-map "inventory_common:PortSlot";
        key "name";
        description "Port slot number";

        container port {
          xr:xr-xml-map "inventory_common:Port";
          description "Port";
          uses ATTRIBUTES;
        }
        leaf name {
          xr:xr-xml-map "inventory_common:Name";
          type xr:Cisco-ios-xr-string;
          description "Port slot name";
        }
        uses SENSOR-TABLE;
        uses ATTRIBUTES;
      }
    }
  }

  grouping SLOT-TABLE {
    description "Common node of rack, rack";

    container slots {
      xr:xr-xml-map "inventory_common:SlotTable";
      description "Table of slots";

      list slot {
        xr:xr-xml-map "inventory_common:Slot";
        key "name";
        description "Slot name";

        container cards {
          xr:xr-xml-map "inventory_common:CardTable";
          description "Table of cards";

          list card {
            xr:xr-xml-map "inventory_common:Card";
            key "name";
            description "Card number";

            container portses {
              xr:xr-xml-map "inventory_common:PortTable";
              description "Table of spirit port slots";

              list ports {
                xr:xr-xml-map "inventory_common:Ports";
                key "name";
                description "Port number";
                leaf name {
                  xr:xr-xml-map "inventory_common:Name";
                  type xr:Cisco-ios-xr-string;
                  description "Port name";
                }
                uses ATTRIBUTES;
              }
            }

            container hardware-information {
              xr:xr-xml-map "inventory_common:HardwareInformation";
              description "HardwareInformationDir";

              container processor-information {
                xr:xr-xml-map "inventory_common:ProcessorInformatio"+
                  "n";
                description "ProcesorInformation";
                uses INV-PROCESSOR;
              }

              container motherboard-information {
                xr:xr-xml-map "inventory_common:MotherboardInformat"+
                  "ion";
                description "MotherboardInformation";
                uses INV-XML-MOTHERBOARD-INFO;
              }

              container bootflash-information {
                xr:xr-xml-map "inventory_common:BootflashInformatio"+
                  "n";
                description "BootflashInformation";
                uses INV-BOOTFLASH;
              }

              container disk-information {
                xr:xr-xml-map "inventory_common:DiskInformation";
                description "DiskInformation";
                uses INV-XML-DISK-INFO;
              }
            }

            container sub-slots {
              xr:xr-xml-map "inventory_common:SubSlotTable";
              description "Table of subslots";

              list sub-slot {
                xr:xr-xml-map "inventory_common:SubSlot";
                key "name";
                description "Subslot number";

                container module {
                  xr:xr-xml-map "inventory_common:Module";
                  description "Module of a subslot";
                  uses PORT-SLOT-TABLE;
                  uses SENSOR-TABLE;
                  uses ATTRIBUTES;
                }
                leaf name {
                  xr:xr-xml-map "inventory_common:Name";
                  type xr:Cisco-ios-xr-string;
                  description "Subslot name";
                }
                uses ATTRIBUTES;
              }
            }

            container hw-components {
              xr:xr-xml-map "inventory_common:HWComponentTable";
              description "Table of  HW components ";

              list hw-component {
                xr:xr-xml-map "inventory_common:HWComponent";
                key "name";
                description "HW component number";
                leaf name {
                  xr:xr-xml-map "inventory_common:Name";
                  type xr:Cisco-ios-xr-string;
                  description "HW component name";
                }
                uses SENSOR-TABLE;
                uses ATTRIBUTES;
              }
            }
            leaf name {
              xr:xr-xml-map "inventory_common:Name";
              type xr:Cisco-ios-xr-string;
              description "Card name";
            }
            uses PORT-SLOT-TABLE;
            uses SENSOR-TABLE;
            uses ATTRIBUTES;
          }
        }
        leaf name {
          xr:xr-xml-map "inventory_common:Name";
          type xr:Cisco-ios-xr-string;
          description "Slot name";
        }
        uses ATTRIBUTES;
      }
    }
  }

  grouping PLATFORM-COMMON-SLOT-TABLE {
    description "Common node of rack, rack";

    container slots {
      xr:xr-xml-map "platform_common:SlotTable";
      description "Table of slots";

      list slot {
        xr:xr-xml-map "platform_common:Slot";
        key "slot-name";
        description "Slot name";

        container instances {
          xr:xr-xml-map "platform_common:InstanceTable";
          description "Table of Instances";

          list instance {
            xr:xr-xml-map "platform_common:Instance";
            key "instance-name";
            description "Instance name";
            leaf instance-name {
              xr:xr-xml-map "platform_common:InstanceName";
              type string;
              description "Instance name";
            }
            uses STATE;
          }
        }

        container vm {
          xr:xr-xml-map "platform_common:VM";
          description "VM information";
          uses VM-INFO;
        }
        leaf slot-name {
          xr:xr-xml-map "platform_common:SlotName";
          type xr:Cisco-ios-xr-string;
          description "Slot name";
        }
        uses STATE;
      }
    }
  }

  grouping SENSOR-TABLE {
    description
      "Common node of card, module, hw-component,
      port-slot";

    container sensors {
      xr:xr-xml-map "inventory_common:SensorTable";
      description "Table of sensors";

      list sensor {
        xr:xr-xml-map "inventory_common:Sensor";
        key "name";
        description "Sensor number";
        leaf name {
          xr:xr-xml-map "inventory_common:Name";
          type xr:Cisco-ios-xr-string;
          description "Sensor name";
        }
        uses ATTRIBUTES;
      }
    }
  }

  grouping ATTRIBUTES {
    description
      "Common node of rack, rack, slot, card, sub-slot,
      module, port-slot, port, hw-component, sensor,
      ports";

    container attributes {
      xr:xr-xml-map "inventory_common:Attributes";
      description "Attributes";

      container basic-info {
        xr:xr-xml-map "inventory_common:BasicInfo";
        description "Entity attributes";
        uses INV-XML-ENTITY-BASIC-INFO;
      }

      container fru-info {
        xr:xr-xml-map "inventory_common:FRUInfo";
        description "Field Replaceable Unit (FRU) attributes";
        uses INV-XML-FRU-INFO;
      }
    }
  }

  container platform {
    xr:xr-xml-map "platform_oper:Platform";
    config false;
    description "Platform information";

    container racks {
      xr:xr-xml-map "platform_oper:RackTable";
      description "Table of racks";

      list rack {
        xr:xr-xml-map "platform_oper:Rack";
        key "rack-name";
        description "Rack name";
        leaf rack-name {
          xr:xr-xml-map "platform_oper:RackName";
          type xr:Cisco-ios-xr-string;
          description "Rack name";
        }
        uses PLATFORM-COMMON-SLOT-TABLE;
      }
    }
  }

  container platform-inventory {
    xr:xr-xml-map "inventory_oper:PlatformInventory";
    config false;
    description "platform inventory";

    container racks {
      xr:xr-xml-map "inventory_oper:RackTable";
      description "Table of racks";

      list rack {
        xr:xr-xml-map "inventory_oper:Rack";
        key "name";
        description "Rack name";
        leaf name {
          xr:xr-xml-map "inventory_oper:Name";
          type xr:Cisco-ios-xr-string;
          description "Rack name";
        }
        uses SLOT-TABLE;
        uses ATTRIBUTES;
      }
    }
  }
}
