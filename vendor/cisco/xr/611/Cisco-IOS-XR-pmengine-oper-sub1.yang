submodule Cisco-IOS-XR-pmengine-oper-sub1 {

  belongs-to Cisco-IOS-XR-pmengine-oper {
    prefix Cisco-IOS-XR-pmengine-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR pmengine package operational data.

     Copyright (c) 2013-2016 by Cisco Systems, Inc.
     All rights reserved.";

  revision "2015-11-09" {
    description
      "IOS XR 6.0 revision.";
  }

  typedef Pm-sonet-path-width-enum {
    type enumeration {
      enum none {
        value 0;
        description "Sonet Path Width NONE ";
      }
      enum sts1 {
        value 1;
        description "Sonet Path Width STS1 ";
      }
      enum sts3c-stm1 {
        value 2;
        description "Sonet Path Width sts3cSTM1 ";
      }
      enum sts12c-stm4 {
        value 3;
        description "Sonet Path Width sts12cSTM4 ";
      }
      enum sts24c {
        value 4;
        description "Sonet Path Width sts24 ";
      }
      enum sts48c-stm16 {
        value 5;
        description "Sonet Path Width sts48cSTM16 ";
      }
      enum sts192c-stm64 {
        value 6;
        description "Sonet Path Width sts192cSTM64 ";
      }
      enum sts768c-stm256 {
        value 7;
        description "Sonet Path Width sts768cSTM256 ";
      }
    }
    description "Sonet Path Width Enum";
  }
  typedef Pm-prbs-pattern-et {
    type enumeration {
      enum prbs-none {
        value 0;
        description "pn none";
      }
      enum pn31 {
        value 1;
        description "pn31";
      }
      enum pn23 {
        value 2;
        description "pn23";
      }
      enum pn11 {
        value 4;
        description "pn11";
      }
      enum inv-pn31 {
        value 8;
        description "inv pn31";
      }
      enum inv-pn11 {
        value 16;
        description "inv pn11";
      }
    }
    description "PM PRBS Pattern Mode Enum";
  }

  grouping PM-ETHER-PARAM-STRING {
    description "PM ETHER PARAM STRING";
    leaf data {
      xr:xr-xml-map "pmengine_ui:Data";
      type string {
        length "0..10";
      }
      description "the number in the interval";
    }
    leaf threshold {
      xr:xr-xml-map "pmengine_ui:Threshold";
      type string {
        length "0..10";
      }
      description "the threshold users set";
    }
    leaf tca-report {
      xr:xr-xml-map "pmengine_ui:TCAReport";
      type boolean;
      description "enable/disable to report TCA";
    }
    leaf valid {
      xr:xr-xml-map "pmengine_ui:Valid";
      type boolean;
      description "valid";
    }
  }

  grouping PM-ETHER-PARAM {
    description "PM ETHER PARAM";
    leaf data {
      xr:xr-xml-map "pmengine_ui:Data";
      type uint64;
      description "the number in the interval";
    }
    leaf threshold {
      xr:xr-xml-map "pmengine_ui:Threshold";
      type uint64;
      description "the threshold users set";
    }
    leaf tca-report {
      xr:xr-xml-map "pmengine_ui:TCAReport";
      type boolean;
      description "enable/disable to report TCA";
    }
    leaf valid {
      xr:xr-xml-map "pmengine_ui:Valid";
      type boolean;
      description "valid";
    }
  }

  grouping PM-ETHERNET-PARAS {
    description "all paras in ether";

    container rx-pkt {
      description "RX PKT";
      uses PM-ETHER-PARAM;
    }

    container stat-pkt {
      description "STAT PKT";
      uses PM-ETHER-PARAM;
    }

    container octet-stat {
      description "OCTET STAT";
      uses PM-ETHER-PARAM;
    }

    container oversize-pkt-stat {
      description "OVERSIZE PKT";
      uses PM-ETHER-PARAM;
    }

    container fcs-errors-stat {
      description "FCS ERR";
      uses PM-ETHER-PARAM;
    }

    container long-frames-stat {
      description "LONG FRAMES";
      uses PM-ETHER-PARAM;
    }

    container jabber-stat {
      description "JABBER STATS";
      uses PM-ETHER-PARAM;
    }

    container sixty-four-octets {
      description "SIXTY FOUR OCTET";
      uses PM-ETHER-PARAM;
    }

    container ote-octets {
      description "OCTET";
      uses PM-ETHER-PARAM;
    }

    container tff-octets-stat {
      description "TFF OCTET";
      uses PM-ETHER-PARAM;
    }

    container foo-octet-stat {
      description "FOO OCTET";
      uses PM-ETHER-PARAM;
    }

    container oztt-octet-stat {
      description "OZTT OCTET";
      uses PM-ETHER-PARAM;
    }

    container ofoe-octet-stat {
      description "OFO OCTET";
      uses PM-ETHER-PARAM;
    }

    container in-ucast-pkt {
      description "IN UCAST";
      uses PM-ETHER-PARAM;
    }

    container in-mcast-pkt {
      description "IN MCAST";
      uses PM-ETHER-PARAM;
    }

    container in-bcast-pkt {
      description "IN BCAST";
      uses PM-ETHER-PARAM;
    }

    container out-ucast-pkt {
      description "OUT UCAST";
      uses PM-ETHER-PARAM;
    }

    container out-bcast-pkt {
      description "OUT BCAST";
      uses PM-ETHER-PARAM;
    }

    container out-mcast-pkt {
      description "OUT MCAST";
      uses PM-ETHER-PARAM;
    }

    container tx-pkt {
      description "TX PKT";
      uses PM-ETHER-PARAM;
    }

    container if-in-errors {
      description "IFIN ERRORS";
      uses PM-ETHER-PARAM;
    }

    container if-in-octets {
      description "IFIN OCTETS";
      uses PM-ETHER-PARAM;
    }

    container ether-stat-multicast-pkt {
      description "ETHER STAT MULTICAST PKT";
      uses PM-ETHER-PARAM;
    }

    container ether-stat-broadcast-pkt {
      description "ETHER STAT BROADCAST PKT";
      uses PM-ETHER-PARAM;
    }

    container ether-stat-undersized-pkt {
      description "ETHER STAT UNDERSIZED PKT";
      uses PM-ETHER-PARAM;
    }

    container out-octets {
      description "OUT OCTET";
      uses PM-ETHER-PARAM;
    }

    container in-pause-frame {
      description "INPUT PAUSE FRAME";
      uses PM-ETHER-PARAM;
    }

    container in-good-bytes {
      description "INPUT GOOD BYTES";
      uses PM-ETHER-PARAM;
    }

    container in8021q-frames {
      description "INPUT 802 1Q FRAMES";
      uses PM-ETHER-PARAM;
    }

    container in-pkts1519-max-octets {
      description "INPUT PKTS 1519MAX OCTETS";
      uses PM-ETHER-PARAM;
    }

    container in-good-pkts {
      description "INPUT GOOD PKTS";
      uses PM-ETHER-PARAM;
    }

    container in-drop-overrun {
      description "INPUT DROP OVERRUN";
      uses PM-ETHER-PARAM;
    }

    container in-drop-abort {
      description "INPUT DROP ABORT";
      uses PM-ETHER-PARAM;
    }

    container in-drop-invalid-vlan {
      description "INPUT DROP INVALID VLAN";
      uses PM-ETHER-PARAM;
    }

    container in-drop-invalid-dmac {
      description "INPUT DROP INVALID DMAC";
      uses PM-ETHER-PARAM;
    }

    container in-drop-invalid-encap {
      description "INPUT DROP INVALID ENCAP";
      uses PM-ETHER-PARAM;
    }

    container in-drop-other {
      description "INPUT DROP OTHER";
      uses PM-ETHER-PARAM;
    }

    container in-mib-giant {
      description "INPUT MIB GIANT";
      uses PM-ETHER-PARAM;
    }

    container in-mib-jabber {
      description "INPUT MIB JABBER";
      uses PM-ETHER-PARAM;
    }

    container in-mibcrc {
      description "IN MIB CRC";
      uses PM-ETHER-PARAM;
    }

    container in-error-collisions {
      description "IN ERROR COLLISIONS";
      uses PM-ETHER-PARAM;
    }

    container in-error-symbol {
      description "IN ERROR SYMBOL";
      uses PM-ETHER-PARAM;
    }

    container out-good-bytes {
      description "OUT GOOD BYTES";
      uses PM-ETHER-PARAM;
    }

    container out8021q-frames {
      description "OUT 802 1Q FRAMES";
      uses PM-ETHER-PARAM;
    }

    container out-pause-frames {
      description "OUT PAUSE FRAMES";
      uses PM-ETHER-PARAM;
    }

    container out-pkts1519-max-octets {
      description "OUT PKTS 1519 MAX OCTETS";
      uses PM-ETHER-PARAM;
    }

    container out-good-pkts {
      description "OUT GOOD PKTS";
      uses PM-ETHER-PARAM;
    }

    container out-drop-underrun {
      description "OUT DROP UNDERRUN";
      uses PM-ETHER-PARAM;
    }

    container out-drop-abort {
      description "OUT DROP ABORT";
      uses PM-ETHER-PARAM;
    }

    container out-drop-other {
      description "OUT DROP OTHER";
      uses PM-ETHER-PARAM;
    }

    container out-error-other {
      description "OUT ERROR OTHER";
      uses PM-ETHER-PARAM;
    }

    container in-error-giant {
      description "IN ERROR GIANT";
      uses PM-ETHER-PARAM;
    }

    container in-error-runt {
      description "IN ERROR RUNT";
      uses PM-ETHER-PARAM;
    }

    container in-error-jabbers {
      description "IN ERROR JABBERS";
      uses PM-ETHER-PARAM;
    }

    container in-error-fragments {
      description "IN ERROR FRAGMENTS";
      uses PM-ETHER-PARAM;
    }

    container in-error-other {
      description "IN ERROR OTHER";
      uses PM-ETHER-PARAM;
    }

    container in-pkt64-octet {
      description "IN PKT 64 OCTET";
      uses PM-ETHER-PARAM;
    }

    container in-pkts65127-octets {
      description "IN PKTS 65 127OCTETS";
      uses PM-ETHER-PARAM;
    }

    container in-pkts128255-octets {
      description "IN PKTS 128 255 OCTETS";
      uses PM-ETHER-PARAM;
    }

    container in-pkts256511-octets {
      description "IN PKTS 256 511 OCTETS";
      uses PM-ETHER-PARAM;
    }

    container in-pkts5121023-octets {
      description "IN PKTS 512 1023 OCTETS";
      uses PM-ETHER-PARAM;
    }

    container in-pkts10241518-octets {
      description "IN PKTS 1024 1518 OCTETS";
      uses PM-ETHER-PARAM;
    }

    container outpkt64octet {
      description "OUT PKT 64 OCTET";
      uses PM-ETHER-PARAM;
    }

    container out-pkts65127-octets {
      description "OUT PKTS 65 127OCTETS";
      uses PM-ETHER-PARAM;
    }

    container out-pkts128255-octets {
      description "OUT PKTS 128 255 OCTETS";
      uses PM-ETHER-PARAM;
    }

    container out-pkts256511-octets {
      description "OUT PKTS 256 511 OCTETS";
      uses PM-ETHER-PARAM;
    }

    container out-pkts5121023-octets {
      description "OUT PKTS 512 1023 OCTETS";
      uses PM-ETHER-PARAM;
    }

    container out-pkts10241518-octets {
      description "OUT PKTS 1024 1518 OCTETS";
      uses PM-ETHER-PARAM;
    }

    container rx-util {
      description "Rx Utilization in Percent";
      uses PM-ETHER-PARAM-STRING;
    }

    container tx-util {
      description "Tx Utilization in Percent";
      uses PM-ETHER-PARAM-STRING;
    }

    container tx-undersized-pkt {
      description "TX Undersized Pkt";
      uses PM-ETHER-PARAM;
    }

    container tx-oversized-pkt {
      description "TX Oversized Pkt";
      uses PM-ETHER-PARAM;
    }

    container tx-fragments {
      description "TX Fragments";
      uses PM-ETHER-PARAM;
    }

    container tx-jabber {
      description "TX Jabber";
      uses PM-ETHER-PARAM;
    }

    container tx-bad-fcs {
      description "TX Bad Fcs";
      uses PM-ETHER-PARAM;
    }
    leaf index {
      xr:xr-xml-map "pmengine_ui:Index";
      type uint32;
      description "index";
    }
    leaf valid {
      xr:xr-xml-map "pmengine_ui:Valid";
      type boolean;
      description "valid";
    }
    leaf timestamp {
      xr:xr-xml-map "pmengine_ui:Timestamp";
      type string {
        length "0..64";
      }
      description "timestamp";
    }
    leaf last-clear-time {
      xr:xr-xml-map "pmengine_ui:LastClearTime";
      type string {
        length "0..64";
      }
      description "last clear time";
    }
    leaf last-clear30-sec-time {
      xr:xr-xml-map "pmengine_ui:LastClear30SecTime";
      type string {
        length "0..64";
      }
      description "last clear time";
    }
    leaf last-clear15-min-time {
      xr:xr-xml-map "pmengine_ui:LastClear15MinTime";
      type string {
        length "0..64";
      }
      description "last clear time";
    }
    leaf last-clear24-hr-time {
      xr:xr-xml-map "pmengine_ui:LastClear24HrTime";
      type string {
        length "0..64";
      }
      description "last clear time";
    }
    leaf sec30-support {
      xr:xr-xml-map "pmengine_ui:Sec30Support";
      type boolean;
      description "30 sec support";
    }
  }

  grouping PM-OPTICS-PARAMETER-STRING {
    description "one parameter in optics";
    leaf valid {
      xr:xr-xml-map "pmengine_ui:Valid";
      type boolean;
      description "valid";
    }
    leaf minimum {
      xr:xr-xml-map "pmengine_ui:Minimum";
      type string {
        length "0..20";
      }
      description "minimum";
    }
    leaf average {
      xr:xr-xml-map "pmengine_ui:Average";
      type string {
        length "0..20";
      }
      description "average";
    }
    leaf maximum {
      xr:xr-xml-map "pmengine_ui:Maximum";
      type string {
        length "0..20";
      }
      description "maximum";
    }
    leaf minimum-threshold {
      xr:xr-xml-map "pmengine_ui:MinimumThreshold";
      type string {
        length "0..20";
      }
      description "minimun threshold";
    }
    leaf minimum-tca-report {
      xr:xr-xml-map "pmengine_ui:MinimumTCAReport";
      type boolean;
      description "enable/disable to report TCA on min";
    }
    leaf maximum-threshold {
      xr:xr-xml-map "pmengine_ui:MaximumThreshold";
      type string {
        length "0..20";
      }
      description "maximum threshold";
    }
    leaf maximum-tca-report {
      xr:xr-xml-map "pmengine_ui:MaximumTCAReport";
      type boolean;
      description "enable/disable to report TCA on max";
    }
  }

  grouping PM-OPTICS-PARAMETER {
    description "one parameter in optics";
    leaf valid {
      xr:xr-xml-map "pmengine_ui:Valid";
      type boolean;
      description "valid";
    }
    leaf minimum {
      xr:xr-xml-map "pmengine_ui:Minimum";
      type int32;
      description "minimum";
    }
    leaf average {
      xr:xr-xml-map "pmengine_ui:Average";
      type int32;
      description "average";
    }
    leaf maximum {
      xr:xr-xml-map "pmengine_ui:Maximum";
      type int32;
      description "maximum";
    }
    leaf minimum-threshold {
      xr:xr-xml-map "pmengine_ui:MinimumThreshold";
      type int32;
      description "minimun threshold";
    }
    leaf minimum-tca-report {
      xr:xr-xml-map "pmengine_ui:MinimumTCAReport";
      type boolean;
      description "enable/disable to report TCA on min";
    }
    leaf maximum-threshold {
      xr:xr-xml-map "pmengine_ui:MaximumThreshold";
      type int32;
      description "maximum threshold";
    }
    leaf maximum-tca-report {
      xr:xr-xml-map "pmengine_ui:MaximumTCAReport";
      type boolean;
      description "enable/disable to report TCA on max";
    }
  }

  grouping PM-OPTICS-PARAS {
    description "all paras in optics";

    container lbc {
      description "LBC";
      uses PM-OPTICS-PARAMETER;
    }

    container lbc-pc {
      description "LBC in percentage";
      uses PM-OPTICS-PARAMETER-STRING;
    }

    container opt {
      description "OPT";
      uses PM-OPTICS-PARAMETER-STRING;
    }

    container opr {
      description "OPR";
      uses PM-OPTICS-PARAMETER-STRING;
    }

    container cd {
      description "Chromatic Dispersion";
      uses PM-OPTICS-PARAMETER;
    }

    container dgd {
      description "Differential group Delay";
      uses PM-OPTICS-PARAMETER-STRING;
    }

    container pmd {
      description "Polarization Mode Dispersion";
      uses PM-OPTICS-PARAMETER-STRING;
    }

    container osnr {
      description "Optical Signal to Noise Ratio";
      uses PM-OPTICS-PARAMETER-STRING;
    }

    container center-wavelength {
      description "Center Wavelength/Frequency";
      uses PM-OPTICS-PARAMETER-STRING;
    }

    container pdl {
      description "Polarization Dependent Loss";
      uses PM-OPTICS-PARAMETER-STRING;
    }

    container pcr {
      description "Polarization Change Rate";
      uses PM-OPTICS-PARAMETER-STRING;
    }

    container pn {
      description "Phase Noise";
      uses PM-OPTICS-PARAMETER-STRING;
    }
    leaf index {
      xr:xr-xml-map "pmengine_ui:Index";
      type uint32;
      description "index";
    }
    leaf valid {
      xr:xr-xml-map "pmengine_ui:Valid";
      type boolean;
      description "valid";
    }
    leaf timestamp {
      xr:xr-xml-map "pmengine_ui:Timestamp";
      type string {
        length "0..64";
      }
      description "timestamp";
    }
    leaf last-clear-time {
      xr:xr-xml-map "pmengine_ui:LastClearTime";
      type string {
        length "0..64";
      }
      description "last clear time";
    }
    leaf last-clear15-min-time {
      xr:xr-xml-map "pmengine_ui:LastClear15MinTime";
      type string {
        length "0..64";
      }
      description "last clear time";
    }
    leaf last-clear30-sec-time {
      xr:xr-xml-map "pmengine_ui:LastClear30SecTime";
      type string {
        length "0..64";
      }
      description "last clear time";
    }
    leaf last-clear24-hr-time {
      xr:xr-xml-map "pmengine_ui:LastClear24HrTime";
      type string {
        length "0..64";
      }
      description "last clear time";
    }
    leaf sec30-support {
      xr:xr-xml-map "pmengine_ui:Sec30Support";
      type boolean;
      description "30 sec support";
    }
  }

  grouping SONET-FAR-END-LINE-ENTRY {
    description "SONET FAR END LINE ENTRY";

    container far-end-line-e-ss {
      description "The number of Errored Seconds";
      uses PM-SONET-PARAMETER;
    }

    container far-end-line-se-ss {
      description "The number of Severely Errored Seconds";
      uses PM-SONET-PARAMETER;
    }

    container far-end-line-c-vs {
      description "The number of Coding Violations";
      uses PM-SONET-PARAMETER;
    }

    container far-end-line-ua-ss {
      description "The number of Unavailable Seconds";
      uses PM-SONET-PARAMETER;
    }

    container far-end-line-fc-ls {
      description "The number of Failure counts Seconds";
      uses PM-SONET-PARAMETER;
    }
  }

  grouping SONET-LINE-ENTRY {
    description "SONET LINE ENTRY";

    container line-e-ss {
      description "The number of Errored Seconds";
      uses PM-SONET-PARAMETER;
    }

    container line-se-ss {
      description "The number of Severely Errored Seconds";
      uses PM-SONET-PARAMETER;
    }

    container line-c-vs {
      description "The number of Coding Violations";
      uses PM-SONET-PARAMETER;
    }

    container line-ua-ss {
      description "The number of Unavailable Seconds";
      uses PM-SONET-PARAMETER;
    }

    container line-fc-ls {
      description "The number of Failure counts Seconds";
      uses PM-SONET-PARAMETER;
    }
    leaf line-status {
      xr:xr-xml-map "pmengine_ui:LineStatus";
      type int32;
      description " status of the interface";
    }
  }

  grouping PM-SONET-PARAMETER {
    description "pm one parameter";
    leaf data {
      xr:xr-xml-map "pmengine_ui:Data";
      type uint32;
      description "the number in the interval";
    }
    leaf threshold {
      xr:xr-xml-map "pmengine_ui:Threshold";
      type uint32;
      description "the threshold users set";
    }
    leaf tca-report {
      xr:xr-xml-map "pmengine_ui:TCAReport";
      type boolean;
      description "enable/disable to report TCA";
    }
  }

  grouping SONET-SECTION-ENTRY {
    description "SONET SECTION ENTRY";

    container section-e-ss {
      description "The number of Errored Seconds";
      uses PM-SONET-PARAMETER;
    }

    container section-se-ss {
      description "The number of Severely Errored Seconds";
      uses PM-SONET-PARAMETER;
    }

    container section-sef-ss {
      description "The number of Severely Errored Framing Seconds";
      uses PM-SONET-PARAMETER;
    }

    container section-c-vs {
      description "The number of Coding Violations";
      uses PM-SONET-PARAMETER;
    }
    leaf section-status {
      xr:xr-xml-map "pmengine_ui:SectionStatus";
      type int32;
      description " status of the interface";
    }
  }

  grouping PM-SONET-PARAS {
    description "all paras in ocn";

    container section {
      description "SECTION";
      uses SONET-SECTION-ENTRY;
    }

    container line {
      description "LINE";
      uses SONET-LINE-ENTRY;
    }

    container fe-line {
      description "FarEnd LINE";
      uses SONET-FAR-END-LINE-ENTRY;
    }
    leaf index {
      xr:xr-xml-map "pmengine_ui:Index";
      type uint32;
      description "index";
    }
    leaf valid {
      xr:xr-xml-map "pmengine_ui:Valid";
      type boolean;
      description "valid";
    }
    leaf timestamp {
      xr:xr-xml-map "pmengine_ui:Timestamp";
      type string {
        length "0..64";
      }
      description "timestamp";
    }
    leaf last-clear-time {
      xr:xr-xml-map "pmengine_ui:LastClearTime";
      type string {
        length "0..64";
      }
      description "last clear time";
    }
    leaf last-clear15-min-time {
      xr:xr-xml-map "pmengine_ui:LastClear15MinTime";
      type string {
        length "0..64";
      }
      description "last clear time";
    }
    leaf last-clear24-hr-time {
      xr:xr-xml-map "pmengine_ui:LastClear24HrTime";
      type string {
        length "0..64";
      }
      description "last clear time";
    }
  }

  grouping SONET-FAR-END-PATH-ENTRY {
    description "SONET FAR END PATH ENTRY";
    leaf far-end-path-e-ss {
      xr:xr-xml-map "pmengine_ui:FarEndPathESs";
      type uint32;
      units "second";
      description "The number of Errored Seconds";
    }
    leaf far-end-path-se-ss {
      xr:xr-xml-map "pmengine_ui:FarEndPathSESs";
      type uint32;
      units "second";
      description "The number of Severely Errored Seconds";
    }
    leaf far-end-path-c-vs {
      xr:xr-xml-map "pmengine_ui:FarEndPathCVs";
      type uint32;
      description "The number of Coding Violations";
    }
    leaf far-end-path-ua-ss {
      xr:xr-xml-map "pmengine_ui:FarEndPathUASs";
      type uint32;
      units "second";
      description "The number of Unavailable Seconds";
    }
  }

  grouping PM-SONET-PATH-PARAMETER {
    description "pm one parameter";
    leaf data {
      xr:xr-xml-map "pmengine_ui:Data";
      type uint32;
      description "the number in the interval";
    }
    leaf threshold {
      xr:xr-xml-map "pmengine_ui:Threshold";
      type uint32;
      description "the threshold users set";
    }
    leaf tca-report {
      xr:xr-xml-map "pmengine_ui:TCAReport";
      type boolean;
      description "enable/disable to report TCA";
    }
  }

  grouping SONET-PATH-ENTRY {
    description "SONET PATH ENTRY";

    container path-e-ss {
      description "The number of Errored Seconds";
      uses PM-SONET-PATH-PARAMETER;
    }

    container path-se-ss {
      description "The number of Severely Errored Seconds";
      uses PM-SONET-PATH-PARAMETER;
    }

    container path-c-vs {
      description "The number of Coding Violations";
      uses PM-SONET-PATH-PARAMETER;
    }

    container path-ua-ss {
      description "The number of Unavailable Seconds";
      uses PM-SONET-PATH-PARAMETER;
    }
    leaf path-width {
      xr:xr-xml-map "pmengine_ui:PathWidth";
      type Pm-sonet-path-width-enum;
      description "Indicates the type of the SONET/SDH Path";
    }
    leaf path-status {
      xr:xr-xml-map "pmengine_ui:PathStatus";
      type int32;
      description " status of the interface";
    }
  }

  grouping PM-SONET-PATH-PARAS {
    description "all paras in sts";

    container path {
      description "PATH";
      uses SONET-PATH-ENTRY;
    }

    container fe-path {
      description "Far End PATH";
      uses SONET-FAR-END-PATH-ENTRY;
    }
    leaf index {
      xr:xr-xml-map "pmengine_ui:Index";
      type uint32;
      description "index";
    }
    leaf valid {
      xr:xr-xml-map "pmengine_ui:Valid";
      type boolean;
      description "valid";
    }
    leaf timestamp {
      xr:xr-xml-map "pmengine_ui:Timestamp";
      type string {
        length "0..64";
      }
      description "timestamp";
    }
    leaf last-clear-time {
      xr:xr-xml-map "pmengine_ui:LastClearTime";
      type string {
        length "0..64";
      }
      description "last clear time";
    }
    leaf last-clear15-min-time {
      xr:xr-xml-map "pmengine_ui:LastClear15MinTime";
      type string {
        length "0..64";
      }
      description "last clear time";
    }
    leaf last-clear24-hr-time {
      xr:xr-xml-map "pmengine_ui:LastClear24HrTime";
      type string {
        length "0..64";
      }
      description "last clear time";
    }
  }

  grouping STM-FAR-END-LINE-ENTRY {
    description "STM FAR END LINE ENTRY";

    container far-end-line-e-ss {
      description "The number of Errored Seconds";
      uses PM-STM-PARAMETER;
    }

    container far-end-line-es-rs {
      description "The number of Errored Seconds Ratio";
      uses PM-STM-PARAMETER-RATIO;
    }

    container far-end-line-ebb-es {
      description "The number of Background Block Errors";
      uses PM-STM-PARAMETER;
    }

    container far-end-line-bbe-rs {
      description "The number of Background Block Errors";
      uses PM-STM-PARAMETER-RATIO;
    }

    container far-end-line-se-ss {
      description "The number of Severely Errored Second";
      uses PM-STM-PARAMETER;
    }

    container far-end-line-ses-rs {
      description "The number of Severely Errored Second Ratio";
      uses PM-STM-PARAMETER-RATIO;
    }

    container far-end-line-ua-ss {
      description "The number of Unavailable Second";
      uses PM-STM-PARAMETER;
    }

    container far-end-line-e-bs {
      description "The number of Errored Block Second";
      uses PM-STM-PARAMETER;
    }
  }

  grouping STM-LINE-ENTRY {
    description "STM LINE ENTRY";

    container line-e-ss {
      description "The number of Errored Seconds";
      uses PM-STM-PARAMETER;
    }

    container line-es-rs {
      description "The number of Errored Seconds Ratio";
      uses PM-STM-PARAMETER-RATIO;
    }

    container line-bb-es {
      description "The number of Background Block Errors";
      uses PM-STM-PARAMETER;
    }

    container line-bbe-rs {
      description "The number of Background Block Errors";
      uses PM-STM-PARAMETER-RATIO;
    }

    container line-se-ss {
      description "The number of Severely Errored Second";
      uses PM-STM-PARAMETER;
    }

    container line-ses-rs {
      description "The number of Severely Errored Second Ratio";
      uses PM-STM-PARAMETER-RATIO;
    }

    container line-ua-ss {
      description "The number of Unavailable Second";
      uses PM-STM-PARAMETER;
    }

    container line-e-bs {
      description "The number of Errored Block Second";
      uses PM-STM-PARAMETER;
    }
    leaf line-status {
      xr:xr-xml-map "pmengine_ui:LineStatus";
      type int32;
      description " status of the interface";
    }
  }

  grouping PM-STM-PARAMETER-RATIO {
    description "pm one parameter";
    leaf data {
      xr:xr-xml-map "pmengine_ui:Data";
      type string {
        length "0..8";
      }
      description "the number in the interval";
    }
    leaf threshold {
      xr:xr-xml-map "pmengine_ui:Threshold";
      type string {
        length "0..8";
      }
      description "the threshold users set";
    }
    leaf tca-report {
      xr:xr-xml-map "pmengine_ui:TCAReport";
      type boolean;
      description "enable/disable to report TCA";
    }
  }

  grouping PM-STM-PARAMETER {
    description "pm one parameter";
    leaf data {
      xr:xr-xml-map "pmengine_ui:Data";
      type uint32;
      description "the number in the interval";
    }
    leaf threshold {
      xr:xr-xml-map "pmengine_ui:Threshold";
      type uint32;
      description "the threshold users set";
    }
    leaf tca-report {
      xr:xr-xml-map "pmengine_ui:TCAReport";
      type boolean;
      description "enable/disable to report TCA";
    }
  }

  grouping STM-SECTION-ENTRY {
    description "STM SECTION ENTRY";

    container section-e-ss {
      description "The number of Errored Seconds";
      uses PM-STM-PARAMETER;
    }

    container section-es-rs {
      description "The number of Errored Seconds Ratio";
      uses PM-STM-PARAMETER-RATIO;
    }

    container section-bb-es {
      description "The number of Background Block Errors";
      uses PM-STM-PARAMETER;
    }

    container section-bbe-rs {
      description "The number of Background Block Errors";
      uses PM-STM-PARAMETER-RATIO;
    }

    container section-se-ss {
      description "The number of Severely Errored Second";
      uses PM-STM-PARAMETER;
    }

    container section-ses-rs {
      description "The number of Severely Errored Second Ratio";
      uses PM-STM-PARAMETER-RATIO;
    }

    container section-ua-ss {
      description "The number of Unavailable Second";
      uses PM-STM-PARAMETER;
    }

    container section-e-bs {
      description "The number of Errored Block Second";
      uses PM-STM-PARAMETER;
    }
    leaf section-status {
      xr:xr-xml-map "pmengine_ui:SectionStatus";
      type int32;
      description " status of the interface";
    }
  }

  grouping PM-STM-PARAS {
    description "all paras in stm";

    container section {
      description "SECTION";
      uses STM-SECTION-ENTRY;
    }

    container line {
      description "LINE";
      uses STM-LINE-ENTRY;
    }

    container fe-line {
      description "FarEnd LINE";
      uses STM-FAR-END-LINE-ENTRY;
    }
    leaf index {
      xr:xr-xml-map "pmengine_ui:Index";
      type uint32;
      description "index";
    }
    leaf valid {
      xr:xr-xml-map "pmengine_ui:Valid";
      type boolean;
      description "valid";
    }
    leaf timestamp {
      xr:xr-xml-map "pmengine_ui:Timestamp";
      type string {
        length "0..64";
      }
      description "timestamp";
    }
    leaf last-clear-time {
      xr:xr-xml-map "pmengine_ui:LastClearTime";
      type string {
        length "0..64";
      }
      description "last clear time";
    }
    leaf last-clear15-min-time {
      xr:xr-xml-map "pmengine_ui:LastClear15MinTime";
      type string {
        length "0..64";
      }
      description "last clear time";
    }
    leaf last-clear24-hr-time {
      xr:xr-xml-map "pmengine_ui:LastClear24HrTime";
      type string {
        length "0..64";
      }
      description "last clear time";
    }
  }

  grouping PM-FEC-PARAM-STRING {
    description "pm avg fec parameter";
    leaf minimum {
      xr:xr-xml-map "pmengine_ui:Minimum";
      type string {
        length "0..20";
      }
      description "minimum";
    }
    leaf average {
      xr:xr-xml-map "pmengine_ui:Average";
      type string {
        length "0..20";
      }
      description "average";
    }
    leaf maximum {
      xr:xr-xml-map "pmengine_ui:Maximum";
      type string {
        length "0..20";
      }
      description "maximum";
    }
    leaf minimum-threshold {
      xr:xr-xml-map "pmengine_ui:MinimumThreshold";
      type string {
        length "0..20";
      }
      description "minimun threshold";
    }
    leaf minimum-tca-report {
      xr:xr-xml-map "pmengine_ui:MinimumTCAReport";
      type boolean;
      description "enable/disable to report TCA on min";
    }
    leaf maximum-threshold {
      xr:xr-xml-map "pmengine_ui:MaximumThreshold";
      type string {
        length "0..20";
      }
      description "maximum threshold";
    }
    leaf maximum-tca-report {
      xr:xr-xml-map "pmengine_ui:MaximumTCAReport";
      type boolean;
      description "enable/disable to report TCA";
    }
    leaf valid {
      xr:xr-xml-map "pmengine_ui:Valid";
      type boolean;
      description "valid";
    }
  }

  grouping PM-FEC-PARAM {
    description "pm avg fec param";
    leaf data {
      xr:xr-xml-map "pmengine_ui:Data";
      type uint64;
      description "the number in the interval";
    }
    leaf threshold {
      xr:xr-xml-map "pmengine_ui:Threshold";
      type uint64;
      description "the threshold users set";
    }
    leaf tca-report {
      xr:xr-xml-map "pmengine_ui:TCAReport";
      type boolean;
      description "enable/disable to report TCA";
    }
    leaf valid {
      xr:xr-xml-map "pmengine_ui:Valid";
      type boolean;
      description "valid";
    }
  }

  grouping PM-FEC-PARAS {
    description "all paras in fec";

    container ec-bits {
      description "EC BITS";
      uses PM-FEC-PARAM;
    }

    container uc-words {
      description "UC WORDS";
      uses PM-FEC-PARAM;
    }

    container pre-fec-ber {
      description "Pre FEC BER";
      uses PM-FEC-PARAM-STRING;
    }

    container post-fec-ber {
      description "Post FEC BER";
      uses PM-FEC-PARAM-STRING;
    }

    container q {
      description "Q";
      uses PM-FEC-PARAM-STRING;
    }

    container qmargin {
      description "Q Margin";
      uses PM-FEC-PARAM-STRING;
    }
    leaf index {
      xr:xr-xml-map "pmengine_ui:Index";
      type uint32;
      description "index";
    }
    leaf valid {
      xr:xr-xml-map "pmengine_ui:Valid";
      type boolean;
      description "valid";
    }
    leaf timestamp {
      xr:xr-xml-map "pmengine_ui:Timestamp";
      type string {
        length "0..64";
      }
      description "timestamp";
    }
    leaf last-clear-time {
      xr:xr-xml-map "pmengine_ui:LastClearTime";
      type string {
        length "0..64";
      }
      description "last clear time";
    }
    leaf last-clear15-min-time {
      xr:xr-xml-map "pmengine_ui:LastClear15MinTime";
      type string {
        length "0..64";
      }
      description "last clear time";
    }
    leaf last-clear30-sec-time {
      xr:xr-xml-map "pmengine_ui:LastClear30SecTime";
      type string {
        length "0..64";
      }
      description "last clear time";
    }
    leaf last-clear24-hr-time {
      xr:xr-xml-map "pmengine_ui:LastClear24HrTime";
      type string {
        length "0..64";
      }
      description "last clear time";
    }
    leaf sec30-support {
      xr:xr-xml-map "pmengine_ui:Sec30Support";
      type boolean;
      description "30 sec support";
    }
  }

  grouping PM-OTN-PARAMETER-RATIO {
    description "pm one parameter";
    leaf data {
      xr:xr-xml-map "pmengine_ui:Data";
      type string {
        length "0..8";
      }
      description "the number in the interval";
    }
    leaf threshold {
      xr:xr-xml-map "pmengine_ui:Threshold";
      type string {
        length "0..8";
      }
      description "the threshold users set";
    }
    leaf tca-report {
      xr:xr-xml-map "pmengine_ui:TCAReport";
      type boolean;
      description "enable/disable to report TCA";
    }
  }

  grouping PM-OTN-PARAMETER {
    description "pm one parameter";
    leaf data {
      xr:xr-xml-map "pmengine_ui:Data";
      type uint32;
      description "the number in the interval";
    }
    leaf threshold {
      xr:xr-xml-map "pmengine_ui:Threshold";
      type uint32;
      description "the threshold users set";
    }
    leaf tca-report {
      xr:xr-xml-map "pmengine_ui:TCAReport";
      type boolean;
      description "enable/disable to report TCA";
    }
  }

  grouping PM-OTN-PARAS {
    description "all paras in otn";

    container lbc {
      description "LBC";
      uses PM-OTN-PARAMETER;
    }

    container es-ne {
      description "ES SM NE";
      uses PM-OTN-PARAMETER;
    }

    container esr-ne {
      description "ESR PM NE";
      uses PM-OTN-PARAMETER-RATIO;
    }

    container ses-ne {
      description "SES SM NE";
      uses PM-OTN-PARAMETER;
    }

    container sesr-ne {
      description "SESR SM NE";
      uses PM-OTN-PARAMETER-RATIO;
    }

    container uas-ne {
      description "UAS SM NE";
      uses PM-OTN-PARAMETER;
    }

    container bbe-ne {
      description "BBE SM NE";
      uses PM-OTN-PARAMETER;
    }

    container bber-ne {
      description "BBER SM NE";
      uses PM-OTN-PARAMETER-RATIO;
    }

    container fc-ne {
      description "FC SM NE";
      uses PM-OTN-PARAMETER;
    }

    container es-fe {
      description "ES SM FE";
      uses PM-OTN-PARAMETER;
    }

    container esr-fe {
      description "ESR PM FE";
      uses PM-OTN-PARAMETER-RATIO;
    }

    container ses-fe {
      description "SES SM FE";
      uses PM-OTN-PARAMETER;
    }

    container sesr-fe {
      description "SESR SM FE";
      uses PM-OTN-PARAMETER-RATIO;
    }

    container uas-fe {
      description "UAS SM FE";
      uses PM-OTN-PARAMETER;
    }

    container bbe-fe {
      description "BBE SM FE";
      uses PM-OTN-PARAMETER;
    }

    container bber-fe {
      description "BBER SM FE";
      uses PM-OTN-PARAMETER-RATIO;
    }

    container fc-fe {
      description "FC SM FE";
      uses PM-OTN-PARAMETER;
    }
    leaf index {
      xr:xr-xml-map "pmengine_ui:Index";
      type uint32;
      description "index";
    }
    leaf valid {
      xr:xr-xml-map "pmengine_ui:Valid";
      type boolean;
      description "valid";
    }
    leaf timestamp {
      xr:xr-xml-map "pmengine_ui:Timestamp";
      type string {
        length "0..64";
      }
      description "timestamp";
    }
    leaf last-clear-time {
      xr:xr-xml-map "pmengine_ui:LastClearTime";
      type string {
        length "0..64";
      }
      description "last clear time";
    }
    leaf last-clear15-min-time {
      xr:xr-xml-map "pmengine_ui:LastClear15MinTime";
      type string {
        length "0..64";
      }
      description "last clear time";
    }
    leaf last-clear30-sec-time {
      xr:xr-xml-map "pmengine_ui:LastClear30SecTime";
      type string {
        length "0..64";
      }
      description "last clear time";
    }
    leaf last-clear24-hr-time {
      xr:xr-xml-map "pmengine_ui:LastClear24HrTime";
      type string {
        length "0..64";
      }
      description "last clear time";
    }
    leaf sec30-support {
      xr:xr-xml-map "pmengine_ui:Sec30Support";
      type boolean;
      description "30 sec support";
    }
  }

  grouping PM-PRBS-PARAMETER {
    description "one parameter in optics";
    leaf valid {
      xr:xr-xml-map "pmengine_ui:Valid";
      type boolean;
      description "valid";
    }
    leaf rcv-patt {
      xr:xr-xml-map "pmengine_ui:RcvPatt";
      type Pm-prbs-pattern-et;
      description "RCVD PTRN";
    }
  }

  grouping PM-PRBS-PARAS {
    description "all paras in prbs";

    container rcv-patt {
      description "RCVD PTRN";
      uses PM-PRBS-PARAMETER;
    }
    leaf index {
      xr:xr-xml-map "pmengine_ui:Index";
      type uint32;
      description "index";
    }
    leaf valid {
      xr:xr-xml-map "pmengine_ui:Valid";
      type boolean;
      description "valid";
    }
    leaf timestamp {
      xr:xr-xml-map "pmengine_ui:Timestamp";
      type string {
        length "0..64";
      }
      description "timestamp";
    }
    leaf last-clear-time {
      xr:xr-xml-map "pmengine_ui:LastClearTime";
      type string {
        length "0..64";
      }
      description "last clear time";
    }
    leaf last-clear15-min-time {
      xr:xr-xml-map "pmengine_ui:LastClear15MinTime";
      type string {
        length "0..64";
      }
      description "last clear time";
    }
    leaf last-clear24-hr-time {
      xr:xr-xml-map "pmengine_ui:LastClear24HrTime";
      type string {
        length "0..64";
      }
      description "last clear time";
    }
    leaf ebc {
      xr:xr-xml-map "pmengine_ui:Ebc";
      type uint64;
      description "EBC";
    }
    leaf found-count {
      xr:xr-xml-map "pmengine_ui:FoundCount";
      type uint32;
      description "FOUND COUNT";
    }
    leaf lost-count {
      xr:xr-xml-map "pmengine_ui:LostCount";
      type uint32;
      description "LOST COUNT";
    }
    leaf found-at-time {
      xr:xr-xml-map "pmengine_ui:FoundAtTime";
      type string {
        length "0..64";
      }
      description "FOUND AT TS";
    }
    leaf lost-at-time {
      xr:xr-xml-map "pmengine_ui:LostAtTime";
      type string {
        length "0..64";
      }
      description "LOST AT TS";
    }
    leaf conf-patt {
      xr:xr-xml-map "pmengine_ui:ConfPatt";
      type Pm-prbs-pattern-et;
      description "CONFIG PTRN";
    }
  }

  grouping PM-GFP-PARAM {
    description "PM GFP PARAM";
    leaf data {
      xr:xr-xml-map "pmengine_ui:Data";
      type uint64;
      description "the number in the interval";
    }
    leaf threshold {
      xr:xr-xml-map "pmengine_ui:Threshold";
      type uint64;
      description "the threshold users set";
    }
    leaf tca-report {
      xr:xr-xml-map "pmengine_ui:TCAReport";
      type boolean;
      description "enable/disable to report TCA";
    }
  }

  grouping PM-GFP-PARAS {
    description "PM GFP PARAS";

    container rx-bit-err {
      description "RX BIT ERR";
      uses PM-GFP-PARAM;
    }

    container rx-inv-typ {
      description "RX INV TYP";
      uses PM-GFP-PARAM;
    }

    container rx-crc {
      description "RX CRC";
      uses PM-GFP-PARAM;
    }

    container rx-lfd {
      description "RX LFD";
      uses PM-GFP-PARAM;
    }

    container rx-csf {
      description "RX CSF";
      uses PM-GFP-PARAM;
    }
    leaf index {
      xr:xr-xml-map "pmengine_ui:Index";
      type uint32;
      description "index";
    }
    leaf valid {
      xr:xr-xml-map "pmengine_ui:Valid";
      type boolean;
      description "valid";
    }
    leaf timestamp {
      xr:xr-xml-map "pmengine_ui:Timestamp";
      type string {
        length "0..64";
      }
      description "timestamp";
    }
    leaf last-clear-time {
      xr:xr-xml-map "pmengine_ui:LastClearTime";
      type string {
        length "0..64";
      }
      description "last clear time";
    }
    leaf last-clear15-min-time {
      xr:xr-xml-map "pmengine_ui:LastClear15MinTime";
      type string {
        length "0..64";
      }
      description "last clear time";
    }
    leaf last-clear30-sec-time {
      xr:xr-xml-map "pmengine_ui:LastClear30SecTime";
      type string {
        length "0..64";
      }
      description "last clear time";
    }
    leaf last-clear24-hr-time {
      xr:xr-xml-map "pmengine_ui:LastClear24HrTime";
      type string {
        length "0..64";
      }
      description "last clear time";
    }
    leaf sec30-support {
      xr:xr-xml-map "pmengine_ui:Sec30Support";
      type boolean;
      description "30 sec support";
    }
  }

  grouping HO-VC-FAR-END-PATH-ENTRY {
    description "HO VC FAR END PATH ENTRY";
    leaf far-end-path-e-ss {
      xr:xr-xml-map "pmengine_ui:FarEndPathESs";
      type uint32;
      units "second";
      description "The number of Errored Seconds";
    }
    leaf far-end-path-se-ss {
      xr:xr-xml-map "pmengine_ui:FarEndPathSESs";
      type uint32;
      units "second";
      description "The number of Severely Errored Seconds";
    }
    leaf far-end-path-c-vs {
      xr:xr-xml-map "pmengine_ui:FarEndPathCVs";
      type uint32;
      description "The number of Coding Violations";
    }
    leaf far-end-path-ua-ss {
      xr:xr-xml-map "pmengine_ui:FarEndPathUASs";
      type uint32;
      units "second";
      description "The number of Unavailable Seconds";
    }
  }

  grouping PM-HO-VC-PARAMETER-RATIO {
    description "pm one parameter";
    leaf data {
      xr:xr-xml-map "pmengine_ui:Data";
      type string {
        length "0..8";
      }
      description "the number in the interval";
    }
    leaf threshold {
      xr:xr-xml-map "pmengine_ui:Threshold";
      type string {
        length "0..8";
      }
      description "the threshold users set";
    }
    leaf tca-report {
      xr:xr-xml-map "pmengine_ui:TCAReport";
      type boolean;
      description "enable/disable to report TCA";
    }
  }

  grouping PM-HO-VC-PARAMETER {
    description "pm one parameter";
    leaf data {
      xr:xr-xml-map "pmengine_ui:Data";
      type uint32;
      description "the number in the interval";
    }
    leaf threshold {
      xr:xr-xml-map "pmengine_ui:Threshold";
      type uint32;
      description "the threshold users set";
    }
    leaf tca-report {
      xr:xr-xml-map "pmengine_ui:TCAReport";
      type boolean;
      description "enable/disable to report TCA";
    }
  }

  grouping HO-VC-ENTRY {
    description "HO VC ENTRY";

    container path-e-ss {
      description "The number of Errored Seconds";
      uses PM-HO-VC-PARAMETER;
    }

    container path-es-rs {
      description "The number of Errored Seconds";
      uses PM-HO-VC-PARAMETER-RATIO;
    }

    container path-se-ss {
      description "The number of Severely Errored Seconds";
      uses PM-HO-VC-PARAMETER;
    }

    container path-ses-rs {
      description "The number of Severely Errored Seconds";
      uses PM-HO-VC-PARAMETER-RATIO;
    }

    container path-e-bs {
      description "The number of Errored blocks";
      uses PM-HO-VC-PARAMETER;
    }

    container path-ua-ss {
      description "The number of Unavailable Seconds";
      uses PM-HO-VC-PARAMETER;
    }

    container path-bb-es {
      description "The number of background block errors";
      uses PM-HO-VC-PARAMETER;
    }

    container path-bbe-rs {
      description "The number of background block errors";
      uses PM-HO-VC-PARAMETER-RATIO;
    }
    leaf path-status {
      xr:xr-xml-map "pmengine_ui:PathStatus";
      type int32;
      description " status of the interface";
    }
  }

  grouping PM-HO-VC-PARAS {
    description "all paras in ho_vc";

    container path {
      description "PATH";
      uses HO-VC-ENTRY;
    }

    container fe-path {
      description "Far End PATH";
      uses HO-VC-FAR-END-PATH-ENTRY;
    }
    leaf index {
      xr:xr-xml-map "pmengine_ui:Index";
      type uint32;
      description "index";
    }
    leaf valid {
      xr:xr-xml-map "pmengine_ui:Valid";
      type boolean;
      description "valid";
    }
    leaf timestamp {
      xr:xr-xml-map "pmengine_ui:Timestamp";
      type string {
        length "0..64";
      }
      description "timestamp";
    }
    leaf last-clear-time {
      xr:xr-xml-map "pmengine_ui:LastClearTime";
      type string {
        length "0..64";
      }
      description "last clear time";
    }
    leaf last-clear15-min-time {
      xr:xr-xml-map "pmengine_ui:LastClear15MinTime";
      type string {
        length "0..64";
      }
      description "last clear time";
    }
    leaf last-clear24-hr-time {
      xr:xr-xml-map "pmengine_ui:LastClear24HrTime";
      type string {
        length "0..64";
      }
      description "last clear time";
    }
  }
}
