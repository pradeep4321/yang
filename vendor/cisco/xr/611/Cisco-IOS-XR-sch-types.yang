module Cisco-IOS-XR-sch-types {

  namespace "http://cisco.com/ns/yang/cisco-xr-sch-types";
  prefix "sch";

  organization "Cisco Systems, Inc.";

  contact 
    "Cisco Systems, Inc.
     Postal: 170 W Tasman Drive
     San Jose, CA 95134-1706
     USA

     E-mail: terastream-yang-dev@cisco.com";

  description       
    "XR CDL specific definitions.
    
     Copyright (c) 2013-2016 by Cisco Systems, Inc.
     All rights reserved.";

  revision "2015-08-06" {
    description
      "Added extenstion for identity str-values and int-values.";
  }

  revision "2013-07-22" {
    description
      "Initial revision.";
  }


  extension bag {
    argument "file_name";
    description "BAG file name.";
  }

  extension bag-dll {
    argument "file_name";
    description "BAG DLL file name.";
  }

  extension bag-encoder {
    argument "encoder";
    description "";
  }

  extension bag-grp-name {
    argument "name";
    description "";
  }

  extension bag-list-next {
    argument "next";
    description "";
  }

  extension bag-name {
    argument "name";
    description "BAG name.";
  }

  extension bag-path {
    argument "path";
    description "";
  }

  extension bag-primitive-type {
    argument "type";
    description "";
  }

  extension bag-version {
    argument "version";
    description "BAG version.";
  }

  extension bind {
    argument "bind";
    description "";
  }

  extension compatibility {
    argument "version";
    description "";
  }

  extension delete-dependent {
    argument "dep";
    description "";
  }

  extension dependent {
    argument "dep";
    description "";
  }

  extension exact {
    description "";
  }

  extension filterlist {
    argument "filter";
    description "";
  }

  extension internal-key {
    argument "key";
    description "";
  }

  extension item {
    description "";
  }

  extension pack-elem-size {
    argument "size";
    description "Size of PACK element (in bytes).";
  }

  extension pack-format {
    argument "format";
    description "Format string specifying format for each PACK
                 element.";
  }

  extension pack-order {
    argument "position";
    description "Position of element in PACK (in bytes).";
  }

  extension pathformat {
    argument "format";
    description "Format string specifying format of naming
                 attributes of element's SysDB path section.";
  }

  extension scope {
    argument "scope";
    description "";
  }

  extension struct {
    argument "file_name";
    description "";
  }

  extension verifier-bgen {
    argument "verifier";
    description "";
  }

  extension verifier-namespace {
    argument "verifier";
    description "";
  }

  extension verifyfns-apply {
    argument "verifyfns";
    description "";
  }

  extension verifyfns-verify {
    argument "verifyfns";
    description "";
  }

  extension identity-int-value {
    argument "identity-int-value";
    description "Integer value for identity representation";
  }

  extension identity-str-value {
    argument "identity-str-value";
    description "String value for identity representation";
  }

  extension xr-cfg-pathname {
    argument "pathname";
    description "";
  }

  extension xr-oper-pathname {
    argument "pathname";
    description "";
  }

  extension xr-primitive-type {
    argument "type";
    description "";
  }

  extension xr-sch-arg-name {
    argument "name";
    description "";
  }

  extension xr-sch-pathname {
    argument "pathname";
    description "SysDB path of element.";
  }

  extension xr-sch-type {
    argument "type";
    description "MDA schema type name.";
  }

  extension xr-task {
    argument "task";
    description "";
  }

  extension xr-create-item-relative-path {
    argument "path";
    description "Notion to create / delete enter element on specified
                 path.";
  }

  extension xr-presence-packed {
    description "Presence container is SysDB packed tuple.";
  }

  extension rpl-func {
    argument "function";
    description "Function name from lib_rpl.dll.";
  }
  
  extension xr-default-set {
    description "Notion to create / delete default values implicitly";
  }

  extension xr-exec {
    argument "exec";
    description "Exec API for action yang models";
  }
}
