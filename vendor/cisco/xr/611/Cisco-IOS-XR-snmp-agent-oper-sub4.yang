submodule Cisco-IOS-XR-snmp-agent-oper-sub4 {

  belongs-to Cisco-IOS-XR-snmp-agent-oper {
    prefix Cisco-IOS-XR-snmp-agent-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR snmp-agent package operational data.

     Copyright (c) 2013-2016 by Cisco Systems, Inc.
     All rights reserved.";

  revision "2015-10-08" {
    description
      "IOS XR 5.3.2 revision.";
  }

  revision "2015-01-07" {
    description
      "IOS XR 5.3.1 revision.";
  }


  grouping SNMP-OVERLOAD-STATS {
    description "SNMP Overload statastics";
    leaf number-of-nmsq-pkts-dropped {
      xr:xr-xml-map "snmp_overload:NumberOfNMSQPktsDropped";
      type uint32;
      description
        "Number of packets which are currently enqueued
        within the NMS queues";
    }
    leaf number-of-pkts-dropped {
      xr:xr-xml-map "snmp_overload:NumberOfPktsDropped";
      type uint32;
      description "Number of packets dropped";
    }
    leaf overload-start-time {
      xr:xr-xml-map "snmp_overload:OverloadStartTime";
      type string;
      description "Time of overload contol begin";
    }
    leaf overload-end-time {
      xr:xr-xml-map "snmp_overload:OverloadEndTime";
      type string;
      description "Time of overload contol End";
    }
  }
}
