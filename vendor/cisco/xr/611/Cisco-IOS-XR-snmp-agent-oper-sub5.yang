submodule Cisco-IOS-XR-snmp-agent-oper-sub5 {

  belongs-to Cisco-IOS-XR-snmp-agent-oper {
    prefix Cisco-IOS-XR-snmp-agent-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR snmp-agent package operational data.

     Copyright (c) 2013-2016 by Cisco Systems, Inc.
     All rights reserved.";

  revision "2015-10-08" {
    description
      "IOS XR 5.3.2 revision.";
  }

  revision "2015-01-07" {
    description
      "IOS XR 5.3.1 revision.";
  }

  typedef Nms-ip {
    type string;
    description "Nms ip";
  }

  grouping SNMP-OID-STATS-B {
    description "SNMP incomming/processing queue statistics";
    leaf nms-count {
      xr:xr-xml-map "snmp_oid_stats_show:NmsCount";
      type uint32;
      description " Managment station count";
    }
    leaf-list nms {
      xr:xr-xml-map "snmp_oid_stats_show:Nms";
      type Nms-ip;
      max-elements "15";
      description "Network Managment station ipadress";
    }
    leaf-list request-count {
      xr:xr-xml-map "snmp_oid_stats_show:RequestCount";
      type uint32;
      max-elements "15";
      description "OID request count for each Managment station ";
    }
  }
}
