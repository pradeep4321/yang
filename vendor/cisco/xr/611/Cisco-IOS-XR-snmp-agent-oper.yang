module Cisco-IOS-XR-snmp-agent-oper {

  /*** NAMESPACE / PREFIX DEFINITION ***/

  namespace "http://cisco.com/ns/yang/Cisco-IOS-XR-snmp-agent-oper";


  prefix "snmp-agent-oper";

  /*** LINKAGE (IMPORTS / INCLUDES) ***/

  import ietf-inet-types { prefix "inet"; }

  import Cisco-IOS-XR-types { prefix "xr"; }

  include Cisco-IOS-XR-snmp-agent-oper-sub6 {
    revision-date 2015-10-08;
  }

  include Cisco-IOS-XR-snmp-agent-oper-sub5 {
    revision-date 2015-10-08;
  }

  include Cisco-IOS-XR-snmp-agent-oper-sub4 {
    revision-date 2015-10-08;
  }

  include Cisco-IOS-XR-snmp-agent-oper-sub3 {
    revision-date 2015-10-08;
  }

  include Cisco-IOS-XR-snmp-agent-oper-sub2 {
    revision-date 2015-10-08;
  }

  include Cisco-IOS-XR-snmp-agent-oper-sub1 {
    revision-date 2015-10-08;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR snmp-agent package operational data.

     This module contains definitions
     for the following management objects:
       snmp: SNMP operational data

     Copyright (c) 2013-2016 by Cisco Systems, Inc.
     All rights reserved.";

  revision "2015-10-08" {
    description
      "IOS XR 5.3.2 revision.";
  }

  revision "2015-01-07" {
    description
      "IOS XR 5.3.1 revision.";
  }


  container snmp {
    xr:xr-xml-map "snmp_oper:SNMP";
    config false;
    description "SNMP operational data";

    container trap-servers {
      xr:xr-xml-map "snmp_oper:TrapServerTable";
      description "List of trap hosts";

      list trap-server {
        xr:xr-xml-map "snmp_oper:TrapServer";
        description
          "Trap server and port to which the trap is to be
          sent and statistics";
        leaf trap-host {
          xr:xr-xml-map "snmp_oper:TrapHost";
          type string;
          description "Trap Host";
        }
        leaf port {
          xr:xr-xml-map "snmp_oper:Port";
          type inet:port-number;
          description "Trap port";
        }
        uses SNMP-TRAP-STATS;
      }
    }

    container information {
      xr:xr-xml-map "snmp_oper:Information";
      description "SNMP operational information";

      container hosts {
        xr:xr-xml-map "snmp_oper:HostTable";
        description "SNMP host information";

        list host {
          xr:xr-xml-map "snmp_oper:Host";
          key "name";
          description "SNMP target host name";
          leaf name {
            xr:xr-xml-map "snmp_oper:Name";
            type xr:Cisco-ios-xr-string;
            description "Group name";
          }

          list host-information {
            xr:xr-xml-map "snmp_oper:HostInformation";
            key "user";
            description
              "Host name ,udp-port , user, security model
              and level";
            leaf user {
              xr:xr-xml-map "snmp_oper:user";
              type xr:Cisco-ios-xr-string;
              description "SNMP host user";
            }
            uses SNMP-SNMP-HOST-XML;
          }
        }
      }

      container system-up-time {
        xr:xr-xml-map "snmp_oper:SystemUpTime";
        description "System up time";
        uses SNMP-SYSUPTIME;
      }

      container nms-addresses {
        xr:xr-xml-map "snmp_oper:RequestTypeSummary";
        description "SNMP request type summary ";

        list nms-address {
          xr:xr-xml-map "snmp_oper:NMSAddress";
          key "nms-addr";
          description "NMS address";
          leaf nms-addr {
            xr:xr-xml-map "snmp_oper:nmsAddr";
            type xr:Cisco-ios-xr-string;
            description "NMS address";
          }
          uses SNMP-REQ-NMS-SUM;
        }
      }

      container engine-id {
        xr:xr-xml-map "snmp_oper:EngineID";
        description "SNMP engine ID";
        uses SNMP-ENGINEID;
      }

      container rx-queue {
        xr:xr-xml-map "snmp_oper:RxQueue";
        description "SNMP rx queue statistics";
        uses SNMP-RXQUE;
      }

      container system-name {
        xr:xr-xml-map "snmp_oper:SystemName";
        description "System name";
        uses SNMP-SYSNAME;
      }

      container request-type-detail {
        xr:xr-xml-map "snmp_oper:RequestTypeDetail";
        description "SNMP request type details ";

        container nms-addresses {
          xr:xr-xml-map "snmp_oper:incomingQ";
          description "snmp request type details ";

          list nms-address {
            xr:xr-xml-map "snmp_oper:NMSAddress";
            key "nms-addr";
            description "NMS address";
            leaf nms-addr {
              xr:xr-xml-map "snmp_oper:nmsAddr";
              type xr:Cisco-ios-xr-string;
              description "NMS address";
            }
            uses SNMP-Q-STATS-B;
          }
        }
      }

      container duplicate-drop {
        xr:xr-xml-map "snmp_oper:DuplicateDrop";
        description "Duplicate request status, count, time ";
        uses SNMP-STATISTICS;
      }

      container bulk-stats-transfers {
        xr:xr-xml-map "snmp_oper:BulkStatsTransferTable";
        description "List of bulkstats transfer on the system";

        list bulk-stats-transfer {
          xr:xr-xml-map "snmp_oper:BulkStatsTransfer";
          key "transfer-name";
          description "SNMP bulkstats transfer name";
          leaf transfer-name {
            xr:xr-xml-map "snmp_oper:TransferName";
            type xr:Cisco-ios-xr-string;
            description "Transfer name";
          }
          uses SNMP-BULKSTATS-B;
        }
      }

      container trap-infos {
        xr:xr-xml-map "snmp_oper:TrapInfoTable";
        description "SNMP trap OID";

        list trap-info {
          xr:xr-xml-map "snmp_oper:TrapInfo";
          description
            "SNMP Trap infomation like server , port and
            trapOID";
          leaf trap-host {
            xr:xr-xml-map "snmp_oper:TrapHost";
            type string;
            description "Trap Host";
          }
          leaf port {
            xr:xr-xml-map "snmp_oper:Port";
            type inet:port-number;
            description "Trap port";
          }
          uses SNMP-TRAPS-INFO;
        }
      }

      container poll-oids {
        xr:xr-xml-map "snmp_oper:PollPDU";
        description "OID list for poll PDU";

        list poll-oid {
          xr:xr-xml-map "snmp_oper:PollOID";
          key "object-id";
          description "PDU drop info for OID";
          leaf object-id {
            xr:xr-xml-map "snmp_oper:ObjectID";
            type xr:Cisco-ios-xr-string;
            description "Object ID";
          }
          uses SNMP-OID-STATS-B;
        }
      }

      container infom-details {
        xr:xr-xml-map "snmp_oper:InfomTable";
        description "SNMP trap OID";

        list infom-detail {
          xr:xr-xml-map "snmp_oper:InfomDetail";
          description
            "SNMP Trap infomation like server , port and
            trapOID";
          leaf trap-host {
            xr:xr-xml-map "snmp_oper:TrapHost";
            type string;
            description "Trap Host";
          }
          leaf port {
            xr:xr-xml-map "snmp_oper:Port";
            type inet:port-number;
            description "Trap port";
          }
          uses SNMP-TRAPS-INFO;
        }
      }

      container statistics {
        xr:xr-xml-map "snmp_oper:Statistics";
        description "SNMP statistics";
        uses SNMP-STATS;
      }

      container incoming-queue {
        xr:xr-xml-map "snmp_oper:IncomingQueue";
        description "Incoming queue details ";
        uses SNMP-INCOMING-Q-STATS-ENTRY;
      }

      container context-mapping {
        xr:xr-xml-map "snmp_oper:ContextMapping";
        description
          "Context name, features name, topology name,
          instance";
        uses SNMP-CTX-MAPPING-XML;
      }

      container trap-oids {
        xr:xr-xml-map "snmp_oper:TrapOIDTable";
        description "SNMP trap OID";

        list trap-oid {
          xr:xr-xml-map "snmp_oper:TrapOID";
          key "trap-oid";
          description "SNMP trap ";
          leaf trap-oid {
            xr:xr-xml-map "snmp_oper:TrapOID";
            type xr:Cisco-ios-xr-string;
            description "Trap object ID";
          }
          uses SNMP-TRAPS-COUNT;
        }
      }

      container nm-spackets {
        xr:xr-xml-map "snmp_oper:OverloadQueue";
        description "SNMP overload statistics ";

        list nm-spacket {
          xr:xr-xml-map "snmp_oper:NMSpacket";
          key "packetcount";
          description "NMS packet drop count";
          leaf packetcount {
            xr:xr-xml-map "snmp_oper:Packetcount";
            type xr:Cisco-ios-xr-string;
            description "NMS packet drop count";
          }
          uses SNMP-OVERLOAD-STATS;
        }
      }

      container mibs {
        xr:xr-xml-map "snmp_oper:MIBTable";
        description "List of MIBS supported on the system";

        list mib {
          xr:xr-xml-map "snmp_oper:MIB";
          key "name";
          description "SNMP MIB Name";

          container oids {
            xr:xr-xml-map "snmp_oper:OIDTable";
            description "List of OIDs per MIB";

            list oid {
              xr:xr-xml-map "snmp_oper:OID";
              key "oid";
              description "Object identifiers of a mib";
              leaf oid {
                xr:xr-xml-map "snmp_oper:OID";
                type string;
                description "Object Identifier";
              }
              leaf oid-name {
                xr:xr-xml-map "snmp_oper:OIDName";
                type string;
                mandatory true;
                description "MIB OID Name";
              }
            }
          }

          container mib-information {
            xr:xr-xml-map "snmp_oper:MIBInformation";
            description "MIB state and information";
            uses SNMP-MIB-INFO;
          }
          leaf name {
            xr:xr-xml-map "snmp_oper:Name";
            type xr:Cisco-ios-xr-string;
            description "MIB Name";
          }
        }
      }

      container statistics-extension {
        xr:xr-xml-map "snmp_oper:StatisticsExtension";
        status "obsolete";
        description "SNMP Statistics Extension";
        uses SNMP-STATISTICS;
      }

      container serial-numbers {
        xr:xr-xml-map "snmp_oper:PDUStatistics";
        description "SNMP statistics pdu ";

        list serial-number {
          xr:xr-xml-map "snmp_oper:SerialNumber";
          description "Serial number";
          leaf number {
            xr:xr-xml-map "snmp_oper:Number";
            type xr:Cisco-ios-xr-string;
            description "Serial number";
          }
          leaf req-id {
            xr:xr-xml-map "snmp_oper:ReqID";
            type int32;
            description "Request ID";
          }
          leaf port {
            xr:xr-xml-map "snmp_oper:Port";
            type inet:port-number;
            description "Port";
          }
          uses SNMP-PDU-STATS;
        }
      }

      container drop-nms-addresses {
        xr:xr-xml-map "snmp_oper:DropPDU";
        description "NMS list for drop PDU";

        list drop-nms-address {
          xr:xr-xml-map "snmp_oper:DropNMSAddress";
          key "nms-addr";
          description "PDU drop info for NMS";
          leaf nms-addr {
            xr:xr-xml-map "snmp_oper:nmsAddr";
            type xr:Cisco-ios-xr-string;
            description "NMS address";
          }
          uses SNMP-PDU-DROP-STATS;
        }
      }

      container views {
        xr:xr-xml-map "snmp_oper:ViewTable";
        description "SNMP view information";

        list view {
          xr:xr-xml-map "snmp_oper:View";
          key "name";
          description "SNMP target view name";
          leaf name {
            xr:xr-xml-map "snmp_oper:Name";
            type xr:Cisco-ios-xr-string;
            description "View name";
          }

          list view-information {
            xr:xr-xml-map "snmp_oper:ViewInformation";
            key "object-id";
            description
              "View name ,familytype, storagetype and status";
            leaf object-id {
              xr:xr-xml-map "snmp_oper:ObjectID";
              type xr:Cisco-ios-xr-string;
              description "SNMP view OID";
            }
            uses SNMP-SNMP-VIEW-XML-ENTRY;
          }
        }
      }

      container system-descr {
        xr:xr-xml-map "snmp_oper:SystemDescr";
        description "System description";
        uses SNMP-SYSDESCR;
      }

      container tables {
        xr:xr-xml-map "snmp_oper:Tables";
        description "List of table";

        container groups {
          xr:xr-xml-map "snmp_oper:GroupTable";
          description "List of vacmAccessTable";

          list group {
            xr:xr-xml-map "snmp_oper:Group";
            key "name";
            description "SNMP group name";

            container group-informations {
              xr:xr-xml-map "snmp_oper:temp";
              description "Group Model";

              list group-information {
                xr:xr-xml-map "snmp_oper:GroupInformation";
                description "Group name ,status  and information";
                leaf modelnumber {
                  xr:xr-xml-map "snmp_oper:Modelnumber";
                  type xr:Cisco-ios-xr-string;
                  description "Model number";
                }
                leaf level {
                  xr:xr-xml-map "snmp_oper:level";
                  type xr:Cisco-ios-xr-string;
                  description "Level";
                }
                uses SNMP-VACM-ACCESS-ENTRY;
              }
            }
            leaf name {
              xr:xr-xml-map "snmp_oper:Name";
              type xr:Cisco-ios-xr-string;
              description "Group Name";
            }
          }
        }

        container user-engine-ids {
          xr:xr-xml-map "snmp_oper:UserTable";
          description "List of User";

          list user-engine-id {
            xr:xr-xml-map "snmp_oper:userEngineId";
            key "engine-id";
            description "SNMP engineId";
            leaf engine-id {
              xr:xr-xml-map "snmp_oper:EngineId";
              type xr:Cisco-ios-xr-string;
              description "SNMP Engine ID";
            }

            list user-name {
              xr:xr-xml-map "snmp_oper:UserName";
              key "user-name";
              description "User name ,storage type ,status ";
              leaf user-name {
                xr:xr-xml-map "snmp_oper:UserName";
                type xr:Cisco-ios-xr-string;
                description "User name";
              }
              uses SNMP-USM-USER-ENTRY;
            }
          }
        }
      }

      container system-oid {
        xr:xr-xml-map "snmp_oper:SystemOID";
        description "System object ID";
        uses SNMP-SYSOBJID;
      }

      container trap-queue {
        xr:xr-xml-map "snmp_oper:TrapQueue";
        description "SNMP trap queue statistics";
        uses SNMP-TRAPQUE;
      }
    }

    container interfaces {
      xr:xr-xml-map "snmp_oper:InterfaceTable";
      description "List of interfaces";

      list interface {
        xr:xr-xml-map "snmp_oper:Interface";
        key "name";
        description "Interface Name";
        leaf name {
          xr:xr-xml-map "snmp_oper:Name";
          type xr:Interface-name;
          description "Interface Name";
        }
        leaf interface-index {
          xr:xr-xml-map "snmp_oper:InterfaceIndex";
          type int32;
          mandatory true;
          description "Interface Index as used by MIB tables";
        }
      }
    }

    container correlator {
      xr:xr-xml-map "snmp_corr_oper:Correlator";
      description "Trap Correlator operational data";

      container rule-details {
        xr:xr-xml-map "snmp_corr_oper:RuleDetailTable";
        description
          "Table that contains the database of correlation
          rule details";

        list rule-detail {
          xr:xr-xml-map "snmp_corr_oper:RuleDetail";
          key "rule-name";
          description "Details of one of the correlation rules";
          leaf rule-name {
            xr:xr-xml-map "snmp_corr_oper:RuleName";
            type string {
              length "0..32";
            }
            description "Correlation Rule Name";
          }
          uses SNMP-CORR-RULE-DETAIL-BAG;
        }
      }

      container buffer-status {
        xr:xr-xml-map "snmp_corr_oper:BufferStatus";
        description
          "Describes buffer utilization and parameters
          configured";
        uses SNMP-CORR-BUFFER-INFO-BAG;
      }

      container rule-set-details {
        xr:xr-xml-map "snmp_corr_oper:RulesetDetailTable";
        description "Table that contains the ruleset detail info";

        list rule-set-detail {
          xr:xr-xml-map "snmp_corr_oper:RulesetDetail";
          key "rule-set-name";
          description "Detail of one of the correlation rulesets";
          leaf rule-set-name {
            xr:xr-xml-map "snmp_corr_oper:RulesetName";
            type string {
              length "0..32";
            }
            description "Ruleset Name";
          }
          uses SNMP-CORR-RULESET-DETAIL-BAG;
        }
      }

      container traps {
        xr:xr-xml-map "snmp_corr_oper:TrapTable";
        description "Correlated traps Table";

        list trap {
          xr:xr-xml-map "snmp_corr_oper:Trap";
          key "entry-id";
          description "One of the correlated traps";
          leaf entry-id {
            xr:xr-xml-map "snmp_corr_oper:EntryID";
            type int32;
            description "Entry ID";
          }
          uses SNMP-CORR-TRAP-BUFFER-BAG;
        }
      }
    }

    container interface-indexes {
      xr:xr-xml-map "snmp_oper:InterfaceIndexTable";
      description "List of index";

      list interface-index {
        xr:xr-xml-map "snmp_oper:InterfaceIndex";
        key "interface-index";
        description "Interface Index";
        leaf interface-index {
          xr:xr-xml-map "snmp_oper:InterfaceIndex";
          type int32;
          description "Interface Index as used by MIB tables";
        }
        leaf interface-name {
          xr:xr-xml-map "snmp_oper:InterfaceName";
          type string;
          mandatory true;
          description "Interface Name";
        }
      }
    }
  }
}
