module Cisco-IOS-XR-snmp-test-trap-act {

    namespace "http://cisco.com/ns/yang/Cisco-IOS-XR-snmp-test-trap-act";
    
    prefix "snmp-test-trap-act";
    
    import Cisco-IOS-XR-sch-types { prefix "csc"; }
    import ietf-inet-types { prefix "inet"; }
    
    organization "Cisco Systems, Inc.";
    
    contact
    "Cisco Systems, Inc.
     Customer Service

     Postal: 170 West Tasman Drive
     San Jose, CA 95134

     Tel: +1 800 553-NETS

     E-mail: cs-yang@cisco.com";
    
    description 
    "This module contains a collection of YANG definitions
     for Cisco IOS-XR action package configuration.

     Copyright (c) 2016 by Cisco Systems, Inc.
     All rights reserved.";
    
    revision "2016-04-17" {
        description
            "IOS XR 6.1.1 revision.";
    }

    rpc snmp-cold-start {
        csc:xr-task "snmp";
        description "Generate SNMPv2-MIB::coldStart";
    }

    rpc snmp-warm-start {
        csc:xr-task "snmp";
        description "Generate SNMPv2-MIB::warmStart";
    }
    
    /* description "interface trap commands */
    rpc interface-link-up {
        csc:xr-task "snmp";
        description "Generate IF-MIB::linkUp";
        input {
            leaf ifindex {
                description
                "interface index for which to generate LinkUp trap";
                type uint32 {
                    range 1..2147483647;
                }
            }
        }
    }

    rpc interface-link-down {
        csc:xr-task "snmp";
        description "Generate IF-MIB::linkDown";
        input {
            leaf ifindex {
                description
                "interface index for which to generate LinkDown trap";
                type uint32 {
                    range 1..2147483647;
                }
            }
        }
    }

    rpc sonet-section-status {
        csc:xr-task "snmp";
        description
        "Generate CISCO-SONET-MIB::ciscoSonetSectionStatusChange";
        input {
            leaf ifindex {
                description
                "interface index for which to generate " +
                "ciscoSonetSectionStatusChange trap";
                type uint32 {
                    range 1..2147483647;
                }
            }
        }
    }

    rpc sonet-line-status {
        csc:xr-task "snmp";
        description
        "Generate CISCO-SONET-MIB::ciscoSonetLineStatusChange";
        input {
            leaf ifindex {
                description
                "interface index for which to generate " +
                "ciscoSonetLineStatusChange trap";
                type uint32 {
                    range 1..2147483647;
                }
            }
        }
    }

    rpc sonet-path-status {
        csc:xr-task "snmp";
        description
        "Generate CISCO-SONET-MIB::ciscoSonetPathStatusChange";
        input {
            leaf ifindex {
                description "interface index for which to generate " +
                "ciscoSonetPathStatusChange trap";
                type uint32 {
                    range 1..2147483647;
                }
            }
        }
    }

    rpc infra-syslog-message-generated {
        csc:xr-task "snmp";
        description
            "Generate CISCO-SYSLOG-MIB::clogMessageGenerated";
    }

    rpc infra-flash-device-inserted {
        csc:xr-task "snmp";
        description 
            "Generate CISCO-FLASH-MIB::ciscoFlashDeviceInsertedNotif";
    }

    rpc infra-flash-device-removed {
        csc:xr-task "snmp";
        description
            "Generate CISCO-FLASH-MIB::ciscoFlashDeviceRemovedNotif";
    }

    rpc infra-redundancy-progression {
        csc:xr-task "snmp";
        description
            "Generate CISCO-RF-MIB::ciscoRFProgressionNotif";
    }

    rpc infra-redundancy-switch {
        csc:xr-task "snmp";
        description
            "Generate CISCO-RF-MIB::ciscoRFSwactNotif";
    }

    rpc infra-bridge-new-root {
        csc:xr-task "snmp";
        description "Generate BRIDGE-MIB::newRoot";
    }

    rpc infra-bridge-topology-change {
        csc:xr-task "snmp";
        description "Generate BRIDGE-MIB::topologyChange";
    }

    rpc infra-config-event {
        csc:xr-task "snmp";
        description "Generate CISCO-CONFIG-MAN-MIB::ciscoConfigManEvent";
    }
    
    rpc entity-sensor-threshold-notification {
        csc:xr-task "snmp";
        description
            "Generate CISCO-ENTITY-SENSOR-MIB::entSensorThresholdNotification";
        input {
            leaf entindex {
                description
                "entity Physical Index for which to generate trap";
                type uint32 {
                    range 1..2147483647;
                }
            }
        }
    }

    rpc entity-fru-power-status-change-failed {
        csc:xr-task "snmp";
        description "oper status changed to failed";
        input {
            leaf entindex {
                description
                "entity Physical Index for which to generate trap";
                type uint32 {
                    range 1..2147483647;
                }
            }
        }
    }

    rpc entity-fru-module-status-change-up {
        csc:xr-task "snmp";
        description "fu trap module status changed as ok";
        input {
            leaf entindex {
                description
                "entity Physical Index for which to generate trap";
                type uint32 {
                    range 1..2147483647;
                }
            }
        }
    }

    rpc entity-fru-module-status-change-down {
        csc:xr-task "snmp";
        description "fu trap module status changed as failed";
        input {
            leaf entindex {
                description
                "entity Physical Index for which to generate trap";
                type uint32 {
                    range 1..2147483647;
                }
            }
        }
    }

    rpc entity-fru-fan-tray-oper-status-up {
        csc:xr-task "snmp";
        description "Generate CISCO-ENTITY-FRU-CONTROL-MIB::cefcFanTrayStatusChange";
        input {
            leaf entindex {
                description
                "entity Physical Index for which to generate trap";
                type uint32 {
                    range 1..2147483647;
                }
            }
        }
    }

    rpc entity-fru-fan-tray-inserted {
        csc:xr-task "snmp";
        description "Generate CISCO-ENTITY-FRU-CONTROL-MIB::cefcFRUInserted";
        input {
            leaf entindex {
                description
                "entity Physical Index for which to generate trap";
                type uint32 {
                    range 1..2147483647;
                }
            }
        }
    }

    rpc entity-fru-fan-tray-removed {
        csc:xr-task "snmp";
        description "Generate CISCO-ENTITY-FRU-CONTROL-MIB::cefcFRURemoved";
        input {
            leaf entindex {
                description "entity Physical Index for which to generate trap";
                type uint32 {
                    range 1..2147483647;
                }
            }
        }
    }

    rpc platform-hfr-bundle-downed-link {
        csc:xr-task "snmp";
        description
            "Generate CISCO-FABRIC-HFR-MIB::cfhBundleDownedLinkNotification";
        input {
            leaf bundle-name {
                description
                    "bundle name for which to generate the trap";
                type string;
            }
        }
    }

    rpc platform-hfr-bundle-state {
        csc:xr-task "snmp";
        description
            "Generate CISCO-FABRIC-HFR-MIB::cfhBundleStateNotification";
        input {
            leaf bundle-name {
                description
                    "bundle name for which to generate the trap";
                type string;
            }
        }
    }

    rpc platform-hfr-plane-state {
        csc:xr-task "snmp";
        description "Generate CISCO-FABRIC-HFR-MIB::cfhPlaneStateNotification";
        input {
            leaf plane-id {
                description
                    "plane identifier for which to generate the trap";
                type uint32;
            }
        }
    }
    
    rpc routing-bgp-established-remote-peer {
        csc:xr-task "snmp";
        description
            "Generate BGP4-MIB::bglEstablishedNotification trap";
        input {
            leaf address {
                description
                "BGP remote peer IP address for which to " +
                "generate the trap";
                type inet:ipv4-address-no-zone;
            }
        }
    }

    rpc routing-bgp-state-change-remote-peer {
        csc:xr-task "snmp";
        description
            "Generate CISCO-BGP-MIB::cbgpBackwardTransition";
        input {
            leaf address {
                description
                "BGP remote peer IP address for which to " +
                "generate the trap";
                type inet:ipv4-address-no-zone;
            }
        }
   }

    rpc routing-ospf-neighbor-state-change {
        csc:xr-task "snmp";
        description "Generate OSPF-TRAP-MIB::ospfNbrStateChange";
        input {
            leaf address {
                description
                "neighbor's IP source address for which to generate the trap";
                type inet:ipv4-address-no-zone;
            }
            leaf ifindex {
                description
                "0 for interfaces having IP addresses or IF-MIB " +
                "ifindex of addressless interface";
                type uint32 {
                    range 0..2147483647;
                }
            }
        }
    }
    
    rpc routing-mpls-ldp-session-down {
        csc:xr-task "snmp";
        description
            "Generate MPLS-LDP-STD-MIB::mplsLdpSessionDown";
        input {
            leaf entity-id {
                description
                    "entity ldp-id in x.x.x.x.y.y format where x.x.x.x " +
                    "is the entity IP address and y.y is the label space";
                type string {
                    length 23;
                }
            }
            leaf entity-index {
                description
                    "entity index for which to generate the trap";
                type uint32 {
                    range 1..4294967295;
                }
            }
            leaf peer-id {
                description
                    "peer ldp-id in x.x.x.x.y.y format where x.x.x.x is " +
                    "the entity IP address and y.y is the label space";
                type string {
                    length 23;
                }
            }
        }
    }

    rpc routing-mpls-tunnel-re-routed {
        csc:xr-task "snmp";
        description
            "Generate MPLS-TE-STD-MIB::mplsTunnelRerouted";
        input {
            leaf index {
                description
                "tunnel index for which to generate the trap";
                type uint32 {
                    range 0..65535;
                }
            }
            leaf instance {
                description
                "tunnel instance for which to generate the trap";
                type uint32 {
                    range 0..65535;
                }
            }
            leaf source {
                description
                "source address for which to generate the trap";
                type inet:ipv4-address-no-zone;
            }
            leaf destination {
                description "destination address for which to generate the trap";
                type inet:ipv4-address-no-zone;
            }
        }
    }

    rpc routing-mpls-tunnel-re-optimized {
        csc:xr-task "snmp";
        description
            "Generate MPLS-TE-STD-MIB::mplsTunnelReoptimized";
        input {
            leaf index {
                description
                "tunnel index for which to generate the trap";
                type uint32 {
                    range 0..65535;
                }
            }
            leaf instance {
                description
                "tunnel instance for which to generate the trap";
                type uint32 {
                    range 0..65535;
                }
            }
            leaf source {
                description
                "source address for which to generate the trap";
                type inet:ipv4-address-no-zone;
            }
            leaf destination {
                description
                "destination address for which to generate the trap";
                    type inet:ipv4-address-no-zone;
            }
        }
    }

    rpc routing-mpls-tunnel-down {
        csc:xr-task "snmp";
        description
            "Generate MPLS-TE-STD-MIB::mplsTunnelDown";
        input {
            leaf index {
                description
                "tunnel index for which to generate the trap";
                type uint32 {
                    range 0..65535;
                }
            }
            leaf instance {
                description
                "tunnel instance for which to generate the trap";
                type uint32 {
                    range 0..65535;
                }
            }
            leaf source {
                description "src address";
                type inet:ipv4-address-no-zone;
            }
            leaf destination {
                description
                "destination address for which to generate the trap";
                type inet:ipv4-address-no-zone;
            }
        }
    }

    rpc all {
        csc:xr-task "snmp";
        description "generate all the supported traps";
    }
}
