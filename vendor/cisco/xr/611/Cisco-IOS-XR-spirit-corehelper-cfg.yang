module Cisco-IOS-XR-spirit-corehelper-cfg {

  /*** NAMESPACE / PREFIX DEFINITION ***/

  namespace "http://cisco.com/ns/yang"+
    "/Cisco-IOS-XR-spirit-corehelper-cfg";


  prefix "spirit-corehelper-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR spirit-corehelper package configuration.

     This module contains definitions
     for the following management objects:
       exception: Core dump configuration commands

     Copyright (c) 2013-2016 by Cisco Systems, Inc.
     All rights reserved.";

  revision "2015-11-09" {
    description
      "IOS XR 6.0 revision.";
  }


  container exception {
    xr:xr-xml-map "corehelper_cfg:Exception";
    description "Core dump configuration commands";

    container file {
      xr:xr-xml-map "corehelper_cfg:File";
      description "Container for the order of preference";

      container choice2 {
        xr:xr-xml-map "corehelper_cfg:Choice2";
        must "(compress and not(lower-limit) and not(higher-limit)"+
          " and file-path and not(filename)) or (compress and"+
          " lower-limit and higher-limit and file-path and"+
          " filename)" {
          description "Describes valid combinations of leafs";
        }
        description "Preference of the dump location";
        leaf compress {
          xr:xr-xml-map "corehelper_cfg:Compress";
          type boolean;
          description
            "Specify 'true' to compress core files dumped
            on this path, 'false' to not compress";
        }
        leaf lower-limit {
          xr:xr-xml-map "corehelper_cfg:LowerLimit";
          type uint32 {
            range "0..4";
          }
          description
            "Lower limit.  This is required if Filename is
            specified.";
        }
        leaf higher-limit {
          xr:xr-xml-map "corehelper_cfg:HigherLimit";
          type uint32 {
            range "5..64";
          }
          description
            "Higher limit.  This is required if Filename is
            specified.";
        }
        leaf file-path {
          xr:xr-xml-map "corehelper_cfg:FilePath";
          type string;
          description "Protocol and directory";
        }
        leaf filename {
          xr:xr-xml-map "corehelper_cfg:Filename";
          type string;
          description "Dump filename";
        }
      }

      container choice1 {
        xr:xr-xml-map "corehelper_cfg:Choice1";
        must "(compress and not(lower-limit) and not(higher-limit)"+
          " and file-path and not(filename)) or (compress and"+
          " lower-limit and higher-limit and file-path and"+
          " filename)" {
          description "Describes valid combinations of leafs";
        }
        description "Preference of the dump location";
        leaf compress {
          xr:xr-xml-map "corehelper_cfg:Compress";
          type boolean;
          description
            "Specify 'true' to compress core files dumped
            on this path, 'false' to not compress";
        }
        leaf lower-limit {
          xr:xr-xml-map "corehelper_cfg:LowerLimit";
          type uint32 {
            range "0..4";
          }
          description
            "Lower limit.  This is required if Filename is
            specified.";
        }
        leaf higher-limit {
          xr:xr-xml-map "corehelper_cfg:HigherLimit";
          type uint32 {
            range "5..64";
          }
          description
            "Higher limit.  This is required if Filename is
            specified.";
        }
        leaf file-path {
          xr:xr-xml-map "corehelper_cfg:FilePath";
          type string;
          description "Protocol and directory";
        }
        leaf filename {
          xr:xr-xml-map "corehelper_cfg:Filename";
          type string;
          description "Dump filename";
        }
      }

      container choice3 {
        xr:xr-xml-map "corehelper_cfg:Choice3";
        must "(compress and not(lower-limit) and not(higher-limit)"+
          " and file-path and not(filename)) or (compress and"+
          " lower-limit and higher-limit and file-path and"+
          " filename)" {
          description "Describes valid combinations of leafs";
        }
        description "Preference of the dump location";
        leaf compress {
          xr:xr-xml-map "corehelper_cfg:Compress";
          type boolean;
          description
            "Specify 'true' to compress core files dumped
            on this path, 'false' to not compress";
        }
        leaf lower-limit {
          xr:xr-xml-map "corehelper_cfg:LowerLimit";
          type uint32 {
            range "0..4";
          }
          description
            "Lower limit.  This is required if Filename is
            specified.";
        }
        leaf higher-limit {
          xr:xr-xml-map "corehelper_cfg:HigherLimit";
          type uint32 {
            range "5..64";
          }
          description
            "Higher limit.  This is required if Filename is
            specified.";
        }
        leaf file-path {
          xr:xr-xml-map "corehelper_cfg:FilePath";
          type string;
          description "Protocol and directory";
        }
        leaf filename {
          xr:xr-xml-map "corehelper_cfg:Filename";
          type string;
          description "Dump filename";
        }
      }
    }
    leaf sparse {
      xr:xr-xml-map "corehelper_cfg:Sparse";
      type boolean;
      description
        "Specify 'true' to enable sparse core dump,
        'false' to disable sparse core dump";
    }
    leaf packet-memory {
      xr:xr-xml-map "corehelper_cfg:PacketMemory";
      type boolean;
      description
        "Specify 'true' to dump packet memory for all
        process, 'false' to disable dump of packet
        memory";
    }
    leaf sparse-size {
      xr:xr-xml-map "corehelper_cfg:SparseSize";
      type uint32 {
        range "1..4095";
      }
      description "Switch to sparse core dump at this size";
    }
    leaf kernel-debugger {
      xr:xr-xml-map "corehelper_cfg:KernelDebugger";
      type empty;
      description "Enable kernel debugger";
    }
  }
}
