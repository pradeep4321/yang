module Cisco-IOS-XR-vservice-cfg {

  /*** NAMESPACE / PREFIX DEFINITION ***/

  namespace "http://cisco.com/ns/yang/Cisco-IOS-XR-vservice-cfg";


  prefix "vservice-cfg";

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR vservice package configuration.

     This module contains definitions
     for the following management objects:
       vservice: configure vservice node

     Copyright (c) 2013-2016 by Cisco Systems, Inc.
     All rights reserved.";

  revision "2015-11-09" {
    description
      "IOS XR 6.0 revision.";
  }

  typedef Sfc-metadata-type1-alloc-format {
    type enumeration {
      enum dc-allocation {
        value 1;
        description "data center allocation";
      }
    }
    description "Sfc metadata type1 alloc format";
  }
  typedef Sfc-sf-transport {
    type enumeration {
      enum vxlan-gpe {
        value 1;
        description "vxlan-gpe transport type";
      }
    }
    description "Sfc sf transport";
  }
  typedef Sfc-metadata-disposition-match {
    type enumeration {
      enum type1-dcalloc-tenant-id {
        value 1;
        description "match type 1";
      }
    }
    description "Sfc metadata disposition match";
  }
  typedef Sfc-metadata-disposition-action {
    type enumeration {
      enum redirect-nexthop {
        value 1;
        description "redirect nexthop action";
      }
    }
    description "Sfc metadata disposition action";
  }
  typedef Sfc-metadata-alloc {
    type enumeration {
      enum type1 {
        value 1;
        description "type 1 allocation";
      }
    }
    description "Sfc metadata alloc";
  }

  grouping NAME-TABLE {
    description
      "Common node of service-function-locator,
      service-function-forward-locator";

    container names {
      xr:xr-xml-map "vservice_cfg:NameTable";
      description "Mention the sf/sff name";

      list name {
        xr:xr-xml-map "vservice_cfg:Name";
        key "function-name locator-id";
        description "service function name";

        container node {
          xr:xr-xml-map "vservice_cfg:Node";
          description "configure sff/sffl";
          leaf transport {
            xr:xr-xml-map "vservice_cfg:Transport";
            type Sfc-sf-transport;
            description "Transport type";
          }
          leaf ipv4-source-address {
            xr:xr-xml-map "vservice_cfg:Ipv4SourceAddress";
            type inet:ipv4-address-no-zone;
            description "IPv4 source address";
          }
          leaf ipv4-destination-address {
            xr:xr-xml-map "vservice_cfg:Ipv4DestinationAddress";
            type inet:ipv4-address-no-zone;
            description "IPv4 destination address";
          }
          leaf source-port {
            xr:xr-xml-map "vservice_cfg:SourcePort";
            type uint32 {
              range "1..65536";
            }
            description "Source Port";
          }
          leaf vni {
            xr:xr-xml-map "vservice_cfg:VNI";
            type int32;
            description "VNI";
          }
        }
        leaf function-name {
          xr:xr-xml-map "vservice_cfg:FunctionName";
          type xr:Cisco-ios-xr-string;
          description "Service function/forwarder name";
        }
        leaf locator-id {
          xr:xr-xml-map "vservice_cfg:LocatorID";
          type uint32 {
            range "1..255";
          }
          description "Specify locator id";
        }
      }
    }
  }

  grouping NODE {
    description "Common node of sf-name, sff-name";

    container node {
      xr:xr-xml-map "vservice_cfg:Node";
      description "configure SFP";
      leaf enable {
        xr:xr-xml-map "vservice_cfg:Enable";
        type empty;
        description "Enable Service function path";
      }
      leaf reserved {
        xr:xr-xml-map "vservice_cfg:Reserved";
        type empty;
        description "Dummy";
      }
    }
  }

  container vservice {
    xr:xr-xml-map "vservice_cfg:Vservice";
    description "configure vservice node";

    container service-function-locator {
      xr:xr-xml-map "vservice_cfg:ServiceFunctionLocator";
      description "configure service function locator";
      uses NAME-TABLE;
    }

    container metadata-dispositions {
      xr:xr-xml-map "vservice_cfg:Disposition";
      description "Configure metadata disposition";

      list metadata-disposition {
        xr:xr-xml-map "vservice_cfg:MetadataDisposition";
        key "disposition-name";
        description "metadata disposition name";
        leaf disposition-name {
          xr:xr-xml-map "vservice_cfg:DispositionName";
          type xr:Cisco-ios-xr-string;
          description "disposition name";
        }

        list match-entry {
          xr:xr-xml-map "vservice_cfg:MatchEntry";
          key "match-entry-name";
          description "match entry name";

          container node {
            xr:xr-xml-map "vservice_cfg:Node";
            description "configure disposition data";
            leaf format {
              xr:xr-xml-map "vservice_cfg:Format";
              type Sfc-metadata-type1-alloc-format;
              description "allocation format";
            }
            leaf match-type {
              xr:xr-xml-map "vservice_cfg:MatchType";
              type Sfc-metadata-disposition-match;
              description "match type";
            }
            leaf action-type {
              xr:xr-xml-map "vservice_cfg:ActionType";
              type Sfc-metadata-disposition-action;
              description "action type";
            }
            leaf vrf {
              xr:xr-xml-map "vservice_cfg:VRF";
              type string;
              description "VRF name";
            }
            leaf nexthop-ipv4-address {
              xr:xr-xml-map "vservice_cfg:NexthopIpv4Address";
              type inet:ipv4-address-no-zone;
              description "IPv4 nexthop address";
            }
            leaf-list tenant-id {
              xr:xr-xml-map "vservice_cfg:TenantIDs";
              type int32;
              max-elements "4";
              description "24-bit tenant id";
            }
          }
          leaf match-entry-name {
            xr:xr-xml-map "vservice_cfg:MatchEntryName";
            type xr:Cisco-ios-xr-string;
            description "match entry name";
          }
        }
      }
    }

    container service-function-forward-locator {
      xr:xr-xml-map "vservice_cfg:ServiceFunctionForwardLocator";
      description "configure service function forward locator";
      uses NAME-TABLE;
    }

    container metadata-templates {
      xr:xr-xml-map "vservice_cfg:MetadataImposition";
      description "configure metadata imposition";

      list metadata-template {
        xr:xr-xml-map "vservice_cfg:MetadataTemplate";
        key "metadata-name type format";
        description "metadata name, type and format";
        leaf node {
          xr:xr-xml-map "vservice_cfg:Node";
          type uint32 {
            range "1..16777215";
          }
          description "Enter 24-bit tenant id";
        }
        leaf metadata-name {
          xr:xr-xml-map "vservice_cfg:MetadataName";
          type xr:Cisco-ios-xr-string;
          description "metadata name";
        }
        leaf type {
          xr:xr-xml-map "vservice_cfg:Type";
          type Sfc-metadata-alloc;
          description "Specify Type ";
        }
        leaf format {
          xr:xr-xml-map "vservice_cfg:Format";
          type Sfc-metadata-type1-alloc-format;
          description "Specify Format";
        }
      }
    }

    container service-function-path {
      xr:xr-xml-map "vservice_cfg:ServiceFunctionPath";
      description "service function path";

      container paths {
        xr:xr-xml-map "vservice_cfg:PathIdTable";
        description "service function path id";

        list path {
          xr:xr-xml-map "vservice_cfg:Path";
          key "path-id";
          description "specify the service function path id";
          leaf path-id {
            xr:xr-xml-map "vservice_cfg:PathId";
            type uint32 {
              range "1..16777215";
            }
            description "Specify the service function path id";
          }

          list service-index {
            xr:xr-xml-map "vservice_cfg:ServiceIndex";
            key "index";
            description "specify the service index";

            container terminate {
              xr:xr-xml-map "vservice_cfg:Terminate";
              description "configure terminate";

              container node {
                xr:xr-xml-map "vservice_cfg:Node";
                description "configure default terminate action";
                leaf action {
                  xr:xr-xml-map "vservice_cfg:Action";
                  type Sfc-metadata-disposition-action;
                  description "default action enum";
                }
                leaf vrf {
                  xr:xr-xml-map "vservice_cfg:VRF";
                  type string;
                  description "nexthop vrf name";
                }
                leaf nexthop-ipv4-address {
                  xr:xr-xml-map "vservice_cfg:NexthopIpv4Address";
                  type inet:ipv4-address-no-zone;
                  description "IPv4 nexthop address";
                }
                leaf metatdata-disposition {
                  xr:xr-xml-map "vservice_cfg:MetatdataDisposition";
                  type string;
                  description "metadata-disposition name";
                }
              }
            }

            container sff-names {
              xr:xr-xml-map "vservice_cfg:ServiceFunctionForwarder";
              description "service function forwarder ";

              list sff-name {
                xr:xr-xml-map "vservice_cfg:SFFName";
                key "name";
                description "service function forwarder name";
                leaf name {
                  xr:xr-xml-map "vservice_cfg:Name";
                  type xr:Cisco-ios-xr-string;
                  description "SFF Name";
                }
                uses NODE;
              }
            }

            container sf-names {
              xr:xr-xml-map "vservice_cfg:ServiceFunction";
              description "service function ";

              list sf-name {
                xr:xr-xml-map "vservice_cfg:SFName";
                key "name";
                description "service function name";
                leaf name {
                  xr:xr-xml-map "vservice_cfg:Name";
                  type xr:Cisco-ios-xr-string;
                  description "SF Name";
                }
                uses NODE;
              }
            }
            leaf index {
              xr:xr-xml-map "vservice_cfg:Index";
              type uint32 {
                range "1..255";
              }
              description "Specify the id of service function";
            }
          }
        }
      }
    }
  }
}
